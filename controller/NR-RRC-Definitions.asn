-- This file was generated by the Objective Systems ASN1C Compiler
-- (http://www.obj-sys.com).  Version: 7.8.1, Date: 23-May-2024.

NR-RRC-Definitions DEFINITIONS AUTOMATIC TAGS ::= BEGIN

-- Parameterized type assignments

SetupRelease {ElementTypeParam} ::= CHOICE {
   release NULL,
   setup ElementTypeParam
}

-- Productions

SIB-ReqInfo-r16 ::= ENUMERATED { sib12(0), sib13(1), sib14(2), sib20-v1700(3), 
   sib21-v1700(4), spare3(5), spare2(6), spare1(7) }

AppLayerBufferLevel-r17 ::= INTEGER (0..30000)

ReestablishmentCause ::= ENUMERATED { reconfigurationFailure(0), 
   handoverFailure(1), otherFailure(2), spare1(3) }

T316-r16 ::= ENUMERATED { ms50(0), ms100(1), ms200(2), ms300(3), ms400(4), 
   ms500(5), ms600(6), ms1000(7), ms1500(8), ms2000(9) }

SL-TimeOffsetEUTRA-r16 ::= ENUMERATED { ms0(0), ms0dot25(1), ms0dot5(2), 
   ms0dot625(3), ms0dot75(4), ms1(5), ms1dot25(6), ms1dot5(7), ms1dot75(8), 
   ms2(9), ms2dot5(10), ms3(11), ms4(12), ms5(13), ms6(14), ms8(15), ms10(16), 
   ms20(17) }

PeriodicRNAU-TimerValue ::= ENUMERATED { min5(0), min10(1), min20(2), min30(3)
   , min60(4), min120(5), min360(6), min720(7) }

PagingCycle ::= ENUMERATED { rf32(0), rf64(1), rf128(2), rf256(3) }

ExtendedPagingCycle-r17 ::= ENUMERATED { rf256(0), rf512(1), rf1024(2), 
   spare1(3) }

-- TAG-LOGICALCHANNELCONFIG-STOP
-- TAG-LOGICALCHANNELIDENTITY-START
LogicalChannelIdentity ::= INTEGER (1..maxLC-ID)

-- TAG-CONFIGUREDGRANTCONFIGINDEX-STOP
-- TAG-CONFIGUREDGRANTCONFIGINDEXMAC-START
ConfiguredGrantConfigIndexMAC-r16 ::= INTEGER (0..maxNrofConfiguredGrantConfigMAC-1-r16)

CG-SDT-ConfigLCH-Restriction-r17 ::= SEQUENCE {
   logicalChannelIdentity-r17 [0] LogicalChannelIdentity,
   configuredGrantType1Allowed-r17 [1] ENUMERATED { true(0) } OPTIONAL, -- Need R
   allowedCG-List-r17 [2] SEQUENCE (SIZE (0..maxNrofConfiguredGrantConfigMAC-1-r16)) OF 
      ConfiguredGrantConfigIndexMAC-r16 OPTIONAL
                                                                                                                         -- Need R
}

-- TAG-PTRS-DOWNLINKCONFIG-STOP
-- TAG-PTRS-UPLINKCONFIG-START
PTRS-UplinkConfig ::= SEQUENCE {
   transformPrecoderDisabled [0] SEQUENCE {
      frequencyDensity [0] SEQUENCE (SIZE (2)) OF INTEGER (1..276) OPTIONAL, -- Need S
      timeDensity [1] SEQUENCE (SIZE (3)) OF INTEGER (0..29) OPTIONAL, -- Need S
      maxNrofPorts [2] ENUMERATED { n1(0), n2(1) },
      resourceElementOffset [3] ENUMERATED { offset01(0), offset10(1), 
         offset11(2) } OPTIONAL, -- Need S
      ptrs-Power [4] ENUMERATED { p00(0), p01(1), p10(2), p11(3) }
   } OPTIONAL, -- Need R
   transformPrecoderEnabled [1] SEQUENCE {
      sampleDensity [0] SEQUENCE (SIZE (5)) OF INTEGER (1..276),
      timeDensityTransformPrecoding [1] ENUMERATED { d2(0) } OPTIONAL -- Need S
   } OPTIONAL,
   ...
}

DMRS-UplinkTransformPrecoding-r16 ::= SEQUENCE {
   pi2BPSK-ScramblingID0 [0] INTEGER (0..65535) OPTIONAL, -- Need S
   pi2BPSK-ScramblingID1 [1] INTEGER (0..65535) OPTIONAL -- Need S
}

-- TAG-DMRS-DOWNLINKCONFIG-STOP
-- TAG-DMRS-UPLINKCONFIG-START
DMRS-UplinkConfig ::= SEQUENCE {
   dmrs-Type [0] ENUMERATED { type2(0) } OPTIONAL, -- Need S
   dmrs-AdditionalPosition [1] ENUMERATED { pos0(0), pos1(1), pos3(2) }
       OPTIONAL, -- Need S
   phaseTrackingRS [2] EXPLICIT CHOICE {
      release [0] NULL,
      setup [1] EXPLICIT PTRS-UplinkConfig
   } OPTIONAL, -- Need M
   maxLength [3] ENUMERATED { len2(0) } OPTIONAL, -- Need S
   transformPrecodingDisabled [4] SEQUENCE {
      scramblingID0 [0] INTEGER (0..65535) OPTIONAL, -- Need S
      scramblingID1 [1] INTEGER (0..65535) OPTIONAL,
      ...,
      [[
         dmrs-Uplink-r16 [2] ENUMERATED { enabled(0) } OPTIONAL
      ]]
   } OPTIONAL, -- Need R
   transformPrecodingEnabled [5] SEQUENCE {
      nPUSCH-Identity [0] INTEGER (0..1007) OPTIONAL, -- Need S
      sequenceGroupHopping [1] ENUMERATED { disabled(0) } OPTIONAL, -- Need S
      sequenceHopping [2] ENUMERATED { enabled(0) } OPTIONAL,
      ...,
      [[
         dmrs-UplinkTransformPrecoding-r16 [3] EXPLICIT CHOICE {
            release [0] NULL,
            setup [1] EXPLICIT DMRS-UplinkTransformPrecoding-r16
         } OPTIONAL
      ]]
   } OPTIONAL,
   ...
}

-- TAG-ADDITIONALSPECTRUMEMISSION-STOP
-- TAG-ALPHA-START
Alpha ::= ENUMERATED { alpha0(0), alpha04(1), alpha05(2), alpha06(3), 
   alpha07(4), alpha08(5), alpha09(6), alpha1(7) }

P0-PUSCH-AlphaSetId ::= INTEGER (0..maxNrofP0-PUSCH-AlphaSets-1)

P0-PUSCH-AlphaSet ::= SEQUENCE {
   p0-PUSCH-AlphaSetId [0] P0-PUSCH-AlphaSetId,
   p0 [1] INTEGER (-16..15) OPTIONAL, -- Need S
   alpha [2] Alpha OPTIONAL -- Need S
}

PUSCH-PathlossReferenceRS-Id ::= INTEGER (0..maxNrofPUSCH-PathlossReferenceRSs-1)

-- TAG-SRS-TPC-COMMANDCONFIG-STOP
-- TAG-SSB-INDEX-START
SSB-Index ::= INTEGER (0..maxNrofSSBs-1)

-- TAG-NZP-CSI-RS-RESOURCE-STOP
-- TAG-NZP-CSI-RS-RESOURCEID-START
NZP-CSI-RS-ResourceId ::= INTEGER (0..maxNrofNZP-CSI-RS-Resources-1)

PUSCH-PathlossReferenceRS ::= SEQUENCE {
   pusch-PathlossReferenceRS-Id [0] PUSCH-PathlossReferenceRS-Id,
   referenceSignal [1] EXPLICIT CHOICE {
      ssb-Index [0] SSB-Index,
      csi-RS-Index [1] NZP-CSI-RS-ResourceId
   }
}

SRI-PUSCH-PowerControlId ::= INTEGER (0..maxNrofSRI-PUSCH-Mappings-1)

SRI-PUSCH-PowerControl ::= SEQUENCE {
   sri-PUSCH-PowerControlId [0] SRI-PUSCH-PowerControlId,
   sri-PUSCH-PathlossReferenceRS-Id [1] PUSCH-PathlossReferenceRS-Id,
   sri-P0-PUSCH-AlphaSetId [2] P0-PUSCH-AlphaSetId,
   sri-PUSCH-ClosedLoopIndex [3] ENUMERATED { i0(0), i1(1) }
}

-- TAG-PUSCH-CONFIGCOMMON-STOP
-- TAG-PUSCH-POWERCONTROL-START
PUSCH-PowerControl ::= SEQUENCE {
   tpc-Accumulation [0] ENUMERATED { disabled(0) } OPTIONAL, -- Need S
   msg3-Alpha [1] Alpha OPTIONAL, -- Need S
   p0-NominalWithoutGrant [2] INTEGER (-202..24) OPTIONAL, -- Need M
   p0-AlphaSets [3] SEQUENCE (SIZE (1..maxNrofP0-PUSCH-AlphaSets)) OF P0-PUSCH-AlphaSet OPTIONAL, -- Need M
   pathlossReferenceRSToAddModList [4] SEQUENCE (SIZE (1..maxNrofPUSCH-PathlossReferenceRSs)) OF 
      PUSCH-PathlossReferenceRS OPTIONAL,
                                                                                                                           -- Need N
   pathlossReferenceRSToReleaseList [5] SEQUENCE (SIZE (1..maxNrofPUSCH-PathlossReferenceRSs)) OF 
      PUSCH-PathlossReferenceRS-Id OPTIONAL,
                                                                                                                            -- Need N
   twoPUSCH-PC-AdjustmentStates [6] ENUMERATED { twoStates(0) } OPTIONAL, -- Need S
   deltaMCS [7] ENUMERATED { enabled(0) } OPTIONAL, -- Need S
   sri-PUSCH-MappingToAddModList [8] SEQUENCE (SIZE (1..maxNrofSRI-PUSCH-Mappings)) OF 
      SRI-PUSCH-PowerControl OPTIONAL,
                                                                                                                           -- Need N
   sri-PUSCH-MappingToReleaseList [9] SEQUENCE (SIZE (1..maxNrofSRI-PUSCH-Mappings)) OF 
      SRI-PUSCH-PowerControlId OPTIONAL
                                                                                                                           -- Need N
}

PUSCH-TimeDomainResourceAllocation ::= SEQUENCE {
   k2 [0] INTEGER (0..32) OPTIONAL, -- Need S
   mappingType [1] ENUMERATED { typeA(0), typeB(1) },
   startSymbolAndLength [2] INTEGER (0..127)
}

-- TAG-PUSCH-SERVINGCELLCONFIG-STOP
-- TAG-PUSCH-TIMEDOMAINRESOURCEALLOCATIONLIST-START
PUSCH-TimeDomainResourceAllocationList ::= SEQUENCE (SIZE (1..maxNrofUL-Allocations)) OF 
   PUSCH-TimeDomainResourceAllocation

-- TAG-BEAMFAILURERECOVERYRSCONFIG-STOP
-- TAG-BETAOFFSETS-START
BetaOffsets ::= SEQUENCE {
   betaOffsetACK-Index1 [0] INTEGER (0..31) OPTIONAL, -- Need S
   betaOffsetACK-Index2 [1] INTEGER (0..31) OPTIONAL, -- Need S
   betaOffsetACK-Index3 [2] INTEGER (0..31) OPTIONAL, -- Need S
   betaOffsetCSI-Part1-Index1 [3] INTEGER (0..31) OPTIONAL, -- Need S
   betaOffsetCSI-Part1-Index2 [4] INTEGER (0..31) OPTIONAL, -- Need S
   betaOffsetCSI-Part2-Index1 [5] INTEGER (0..31) OPTIONAL, -- Need S
   betaOffsetCSI-Part2-Index2 [6] INTEGER (0..31) OPTIONAL -- Need S
}

UCI-OnPUSCH ::= SEQUENCE {
   betaOffsets [0] EXPLICIT CHOICE {
      dynamic [0] SEQUENCE (SIZE (4)) OF BetaOffsets,
      semiStatic [1] BetaOffsets
   } OPTIONAL, -- Need M
   scaling [1] ENUMERATED { f0p5(0), f0p65(1), f0p8(2), f1(3) }
}

MinSchedulingOffsetK2-Values-r16 ::= SEQUENCE (SIZE (1..maxNrOfMinSchedulingOffsetValues-r16)) OF INTEGER (0..maxK2-SchedulingOffset-r16)

UL-AccessConfigListDCI-0-1-r16 ::= SEQUENCE (SIZE (1..64)) OF INTEGER (0..63)

FrequencyHoppingOffsetListsDCI-0-2-r16 ::= SEQUENCE (SIZE (1..4)) OF INTEGER (1..maxNrofPhysicalResourceBlocks-1)
   

UCI-OnPUSCH-DCI-0-2-r16 ::= SEQUENCE {
   betaOffsetsDCI-0-2-r16 [0] EXPLICIT CHOICE {
      dynamicDCI-0-2-r16 [0] EXPLICIT CHOICE {
         oneBit-r16 [0] SEQUENCE (SIZE (2)) OF BetaOffsets,
         twoBits-r16 [1] SEQUENCE (SIZE (4)) OF BetaOffsets
      },
      semiStaticDCI-0-2-r16 [1] BetaOffsets
   } OPTIONAL, -- Need M
   scalingDCI-0-2-r16 [1] ENUMERATED { f0p5(0), f0p65(1), f0p8(2), f1(3) }
}

UCI-OnPUSCH-ListDCI-0-2-r16 ::= SEQUENCE (SIZE (1..2)) OF UCI-OnPUSCH-DCI-0-2-r16
   

PUSCH-Allocation-r16 ::= SEQUENCE {
   mappingType-r16 [0] ENUMERATED { typeA(0), typeB(1) } OPTIONAL, -- Cond NotFormat01-02-Or-TypeA
   startSymbolAndLength-r16 [1] INTEGER (0..127) OPTIONAL, -- Cond NotFormat01-02-Or-TypeA
   startSymbol-r16 [2] INTEGER (0..13) OPTIONAL, -- Cond RepTypeB
   length-r16 [3] INTEGER (1..14) OPTIONAL, -- Cond RepTypeB
   numberOfRepetitions-r16 [4] ENUMERATED { n1(0), n2(1), n3(2), n4(3), n7(4), 
      n8(5), n12(6), n16(7) } OPTIONAL,
   ...,
   [[
      numberOfRepetitionsExt-r17 [5] ENUMERATED { n1(0), n2(1), n3(2), n4(3), 
         n7(4), n8(5), n12(6), n16(7), n20(8), n24(9), n28(10), n32(11), 
         spare4(12), spare3(13), spare2(14), spare1(15) } OPTIONAL,
      numberOfSlotsTBoMS-r17 [6] ENUMERATED { n1(0), n2(1), n4(2), n8(3), 
         spare4(4), spare3(5), spare2(6), spare1(7) } OPTIONAL,
      extendedK2-r17 [7] INTEGER (0..128) OPTIONAL
   ]]
}

PUSCH-TimeDomainResourceAllocation-r16 ::= SEQUENCE {
   k2-r16 [0] INTEGER (0..32) OPTIONAL, -- Need S
   puschAllocationList-r16 [1] SEQUENCE (SIZE (1..maxNrofMultiplePUSCHs-r16)) OF PUSCH-Allocation-r16,
   ...
}

PUSCH-TimeDomainResourceAllocationList-r16 ::= SEQUENCE (SIZE (1..maxNrofUL-Allocations-r16)) OF 
   PUSCH-TimeDomainResourceAllocation-r16

UCI-OnPUSCH-ListDCI-0-1-r16 ::= SEQUENCE (SIZE (1..2)) OF UCI-OnPUSCH

-- TAG-HYSTERESISLOCATION-STOP
-- TAG-INVALIDSYMBOLPATTERN-START
InvalidSymbolPattern-r16 ::= SEQUENCE {
   symbols-r16 [0] EXPLICIT CHOICE {
      oneSlot [0] BIT STRING  (SIZE (14)),
      twoSlots [1] BIT STRING  (SIZE (28))
   },
   periodicityAndPattern-r16 [1] EXPLICIT CHOICE {
      n2 [0] BIT STRING  (SIZE (2)),
      n4 [1] BIT STRING  (SIZE (4)),
      n5 [2] BIT STRING  (SIZE (5)),
      n8 [3] BIT STRING  (SIZE (8)),
      n10 [4] BIT STRING  (SIZE (10)),
      n20 [5] BIT STRING  (SIZE (20)),
      n40 [6] BIT STRING  (SIZE (40))
   } OPTIONAL,
   ...
}

PUSCH-PathlossReferenceRS-Id-v1610 ::= INTEGER (maxNrofPUSCH-PathlossReferenceRSs..maxNrofPUSCH-PathlossReferenceRSs-1-r16)

PUSCH-PathlossReferenceRS-r16 ::= SEQUENCE {
   pusch-PathlossReferenceRS-Id-r16 [0] PUSCH-PathlossReferenceRS-Id-v1610,
   referenceSignal-r16 [1] EXPLICIT CHOICE {
      ssb-Index-r16 [0] SSB-Index,
      csi-RS-Index-r16 [1] NZP-CSI-RS-ResourceId
   }
}

P0-PUSCH-SetId-r16 ::= INTEGER (0..maxNrofSRI-PUSCH-Mappings-1)

P0-PUSCH-r16 ::= INTEGER (-16..15)

P0-PUSCH-Set-r16 ::= SEQUENCE {
   p0-PUSCH-SetId-r16 [0] P0-PUSCH-SetId-r16,
   p0-List-r16 [1] SEQUENCE (SIZE (1..maxNrofP0-PUSCH-Set-r16)) OF P0-PUSCH-r16 OPTIONAL,
   ...
}

PUSCH-PathlossReferenceRS-Id-r17 ::= INTEGER (0..maxNrofPUSCH-PathlossReferenceRSs-1-r16)

AdditionalPCIIndex-r17 ::= INTEGER (1..maxNrofAdditionalPCI-r17)

DummyPathlossReferenceRS-v1710 ::= SEQUENCE {
   pusch-PathlossReferenceRS-Id-r17 [0] PUSCH-PathlossReferenceRS-Id-r17,
   additionalPCI-r17 [1] AdditionalPCIIndex-r17 OPTIONAL -- Need R
}

PUSCH-PowerControl-v1610 ::= SEQUENCE {
   pathlossReferenceRSToAddModListSizeExt-v1610 [0] SEQUENCE (SIZE (1..maxNrofPUSCH-PathlossReferenceRSsDiff-r16)) OF 
      PUSCH-PathlossReferenceRS-r16 OPTIONAL,
                                                                                                                           -- Need N
   pathlossReferenceRSToReleaseListSizeExt-v1610 [1] SEQUENCE (SIZE (1..maxNrofPUSCH-PathlossReferenceRSsDiff-r16)) OF 
      PUSCH-PathlossReferenceRS-Id-v1610 OPTIONAL,
                                                                                                                           -- Need N
   p0-PUSCH-SetList-r16 [2] SEQUENCE (SIZE (1..maxNrofSRI-PUSCH-Mappings)) OF P0-PUSCH-Set-r16 OPTIONAL, -- Need R
   olpc-ParameterSet [3] SEQUENCE {
      olpc-ParameterSetDCI-0-1-r16 [0] INTEGER (1..2) OPTIONAL, -- Need R
      olpc-ParameterSetDCI-0-2-r16 [1] INTEGER (1..2) OPTIONAL -- Need R
   } OPTIONAL,
   ...,
   [[
      sri-PUSCH-MappingToAddModList2-r17 [4] SEQUENCE (SIZE (1..maxNrofSRI-PUSCH-Mappings)) OF 
         SRI-PUSCH-PowerControl OPTIONAL,
      sri-PUSCH-MappingToReleaseList2-r17 [5] SEQUENCE (SIZE (1..maxNrofSRI-PUSCH-Mappings)) OF 
         SRI-PUSCH-PowerControlId OPTIONAL,
      p0-PUSCH-SetList2-r17 [6] SEQUENCE (SIZE (1..maxNrofSRI-PUSCH-Mappings)) OF P0-PUSCH-Set-r16
          OPTIONAL,
      dummy [7] SEQUENCE (SIZE (1..maxNrofPUSCH-PathlossReferenceRSs-r16)) OF DummyPathlossReferenceRS-v1710 OPTIONAL
   ]]
}

UL-AccessConfigListDCI-0-2-r17 ::= SEQUENCE (SIZE (1..64)) OF INTEGER (0..63)

-- TAG-BETAOFFSETS-STOP
-- TAG-BETAOFFSETSCROSSPRI-START
BetaOffsetsCrossPri-r17 ::= SEQUENCE (SIZE (3)) OF INTEGER (0..31)

BetaOffsetsCrossPriSel-r17 ::= CHOICE {
   dynamic-r17 [0] SEQUENCE (SIZE (4)) OF BetaOffsetsCrossPri-r17,
   semiStatic-r17 [1] BetaOffsetsCrossPri-r17
}

BetaOffsetsCrossPriSelDCI-0-2-r17 ::= CHOICE {
   dynamicDCI-0-2-r17 [0] EXPLICIT CHOICE {
      oneBit-r17 [0] SEQUENCE (SIZE (2)) OF BetaOffsetsCrossPri-r17,
      twoBits-r17 [1] SEQUENCE (SIZE (4)) OF BetaOffsetsCrossPri-r17
   },
   semiStaticDCI-0-2-r17 [1] BetaOffsetsCrossPri-r17
}

UL-AccessConfigListDCI-0-1-r17 ::= SEQUENCE (SIZE (1..3)) OF INTEGER (0..2)

MinSchedulingOffsetK2-Values-r17 ::= SEQUENCE (SIZE (1..maxNrOfMinSchedulingOffsetValues-r16)) OF INTEGER (0..maxK2-SchedulingOffset-r17)

-- TAG-DMRS-BUNDLINGPUCCH-CONFIG-STOP
-- TAG-DMRS-BUNDLINGPUSCH-CONFIG-START
DMRS-BundlingPUSCH-Config-r17 ::= SEQUENCE {
   pusch-DMRS-Bundling-r17 [0] ENUMERATED { enabled(0) } OPTIONAL, -- Need R
   pusch-TimeDomainWindowLength-r17 [1] INTEGER (2..32) OPTIONAL, -- Need S
   pusch-WindowRestart-r17 [2] ENUMERATED { enabled(0) } OPTIONAL, -- Need R
   pusch-FrequencyHoppingInterval-r17 [3] ENUMERATED { s2(0), s4(1), s5(2), 
      s6(3), s8(4), s10(5), s12(6), s14(7), s16(8), s20(9) } OPTIONAL,
   ...
}

MPE-ResourceId-r17 ::= INTEGER (1..maxMPE-Resources-r17)

-- TAG-SERVINGCELLANDBWP-ID-STOP
-- TAG-SERVCELLINDEX-START
ServCellIndex ::= INTEGER (0..maxNrofServingCells-1)

MPE-Resource-r17 ::= SEQUENCE {
   mpe-ResourceId-r17 [0] MPE-ResourceId-r17,
   cell-r17 [1] ServCellIndex OPTIONAL, -- Need R
   additionalPCI-r17 [2] AdditionalPCIIndex-r17 OPTIONAL, -- Need R
   mpe-ReferenceSignal-r17 [3] EXPLICIT CHOICE {
      csi-RS-Resource-r17 [0] NZP-CSI-RS-ResourceId,
      ssb-Resource-r17 [1] SSB-Index
   }
}

-- TAG-PUCCH-TPC-COMMANDCONFIG-STOP
-- TAG-PUSCH-CONFIG-START
PUSCH-Config ::= SEQUENCE {
   dataScramblingIdentityPUSCH [0] INTEGER (0..1023) OPTIONAL, -- Need S
   txConfig [1] ENUMERATED { codebook(0), nonCodebook(1) } OPTIONAL, -- Need S
   dmrs-UplinkForPUSCH-MappingTypeA [2] EXPLICIT CHOICE {
      release [0] NULL,
      setup [1] EXPLICIT DMRS-UplinkConfig
   } OPTIONAL, -- Need M
   dmrs-UplinkForPUSCH-MappingTypeB [3] EXPLICIT CHOICE {
      release [0] NULL,
      setup [1] EXPLICIT DMRS-UplinkConfig
   } OPTIONAL, -- Need M
   pusch-PowerControl [4] PUSCH-PowerControl OPTIONAL, -- Need M
   frequencyHopping [5] ENUMERATED { intraSlot(0), interSlot(1) } OPTIONAL, -- Need S
   frequencyHoppingOffsetLists [6] SEQUENCE (SIZE (1..4)) OF INTEGER (1..maxNrofPhysicalResourceBlocks-1)
       OPTIONAL,
                                                                                                                             -- Need M
   resourceAllocation [7] ENUMERATED { resourceAllocationType0(0), 
      resourceAllocationType1(1), dynamicSwitch(2) },
   pusch-TimeDomainAllocationList [8] EXPLICIT CHOICE {
      release [0] NULL,
      setup [1] EXPLICIT PUSCH-TimeDomainResourceAllocationList
   } OPTIONAL, -- Need M
   pusch-AggregationFactor [9] ENUMERATED { n2(0), n4(1), n8(2) } OPTIONAL, -- Need S
   mcs-Table [10] ENUMERATED { qam256(0), qam64LowSE(1) } OPTIONAL, -- Need S
   mcs-TableTransformPrecoder [11] ENUMERATED { qam256(0), qam64LowSE(1) }
       OPTIONAL, -- Need S
   transformPrecoder [12] ENUMERATED { enabled(0), disabled(1) } OPTIONAL, -- Need S
   codebookSubset [13] ENUMERATED { fullyAndPartialAndNonCoherent(0), 
      partialAndNonCoherent(1), nonCoherent(2) } OPTIONAL,
                                                                                                                     -- Cond codebookBased
   maxRank [14] INTEGER (1..4) OPTIONAL, -- Cond codebookBased
   rbg-Size [15] ENUMERATED { config2(0) } OPTIONAL, -- Need S
   uci-OnPUSCH [16] EXPLICIT CHOICE {
      release [0] NULL,
      setup [1] EXPLICIT UCI-OnPUSCH
   } OPTIONAL, -- Need M
   tp-pi2BPSK [17] ENUMERATED { enabled(0) } OPTIONAL,
   ...,
   [[
      minimumSchedulingOffsetK2-r16 [18] EXPLICIT CHOICE {
         release [0] NULL,
         setup [1] EXPLICIT MinSchedulingOffsetK2-Values-r16
      } OPTIONAL,
      ul-AccessConfigListDCI-0-1-r16 [19] EXPLICIT CHOICE {
         release [0] NULL,
         setup [1] EXPLICIT UL-AccessConfigListDCI-0-1-r16
      } OPTIONAL,
      harq-ProcessNumberSizeDCI-0-2-r16 [20] INTEGER (0..4) OPTIONAL,
      dmrs-SequenceInitializationDCI-0-2-r16 [21] ENUMERATED { enabled(0) }
          OPTIONAL,
      numberOfBitsForRV-DCI-0-2-r16 [22] INTEGER (0..2) OPTIONAL,
      antennaPortsFieldPresenceDCI-0-2-r16 [23] ENUMERATED { enabled(0) }
          OPTIONAL,
      dmrs-UplinkForPUSCH-MappingTypeA-DCI-0-2-r16 [24] EXPLICIT CHOICE {
         release [0] NULL,
         setup [1] EXPLICIT DMRS-UplinkConfig
      } OPTIONAL,
      dmrs-UplinkForPUSCH-MappingTypeB-DCI-0-2-r16 [25] EXPLICIT CHOICE {
         release [0] NULL,
         setup [1] EXPLICIT DMRS-UplinkConfig
      } OPTIONAL,
      frequencyHoppingDCI-0-2-r16 [26] EXPLICIT CHOICE {
         pusch-RepTypeA [0] ENUMERATED { intraSlot(0), interSlot(1) },
         pusch-RepTypeB [1] ENUMERATED { interRepetition(0), interSlot(1) }
      } OPTIONAL,
      frequencyHoppingOffsetListsDCI-0-2-r16 [27] EXPLICIT CHOICE {
         release [0] NULL,
         setup [1] EXPLICIT FrequencyHoppingOffsetListsDCI-0-2-r16
      } OPTIONAL,
      codebookSubsetDCI-0-2-r16 [28] ENUMERATED { 
         fullyAndPartialAndNonCoherent(0), partialAndNonCoherent(1), 
         nonCoherent(2) } OPTIONAL,
      invalidSymbolPatternIndicatorDCI-0-2-r16 [29] ENUMERATED { enabled(0) }
          OPTIONAL,
      maxRankDCI-0-2-r16 [30] INTEGER (1..4) OPTIONAL,
      mcs-TableDCI-0-2-r16 [31] ENUMERATED { qam256(0), qam64LowSE(1) }
          OPTIONAL,
      mcs-TableTransformPrecoderDCI-0-2-r16 [32] ENUMERATED { qam256(0), 
         qam64LowSE(1) } OPTIONAL,
      priorityIndicatorDCI-0-2-r16 [33] ENUMERATED { enabled(0) } OPTIONAL,
      pusch-RepTypeIndicatorDCI-0-2-r16 [34] ENUMERATED { pusch-RepTypeA(0), 
         pusch-RepTypeB(1) } OPTIONAL,
      resourceAllocationDCI-0-2-r16 [35] ENUMERATED { 
         resourceAllocationType0(0), resourceAllocationType1(1), 
         dynamicSwitch(2) } OPTIONAL,
      resourceAllocationType1GranularityDCI-0-2-r16 [36] ENUMERATED { n2(0), 
         n4(1), n8(2), n16(3) } OPTIONAL,
      uci-OnPUSCH-ListDCI-0-2-r16 [37] EXPLICIT CHOICE {
         release [0] NULL,
         setup [1] EXPLICIT UCI-OnPUSCH-ListDCI-0-2-r16
      } OPTIONAL,
      pusch-TimeDomainAllocationListDCI-0-2-r16 [38] EXPLICIT CHOICE {
         release [0] NULL,
         setup [1] EXPLICIT PUSCH-TimeDomainResourceAllocationList-r16
      } OPTIONAL,
      pusch-TimeDomainAllocationListDCI-0-1-r16 [39] EXPLICIT CHOICE {
         release [0] NULL,
         setup [1] EXPLICIT PUSCH-TimeDomainResourceAllocationList-r16
      } OPTIONAL,
      invalidSymbolPatternIndicatorDCI-0-1-r16 [40] ENUMERATED { enabled(0) }
          OPTIONAL,
      priorityIndicatorDCI-0-1-r16 [41] ENUMERATED { enabled(0) } OPTIONAL,
      pusch-RepTypeIndicatorDCI-0-1-r16 [42] ENUMERATED { pusch-RepTypeA(0), 
         pusch-RepTypeB(1) } OPTIONAL,
      frequencyHoppingDCI-0-1-r16 [43] ENUMERATED { interRepetition(0), 
         interSlot(1) } OPTIONAL,
      uci-OnPUSCH-ListDCI-0-1-r16 [44] EXPLICIT CHOICE {
         release [0] NULL,
         setup [1] EXPLICIT UCI-OnPUSCH-ListDCI-0-1-r16
      } OPTIONAL,
      invalidSymbolPattern-r16 [45] InvalidSymbolPattern-r16 OPTIONAL,
      pusch-PowerControl-v1610 [46] EXPLICIT CHOICE {
         release [0] NULL,
         setup [1] EXPLICIT PUSCH-PowerControl-v1610
      } OPTIONAL,
      ul-FullPowerTransmission-r16 [47] ENUMERATED { fullpower(0), 
         fullpowerMode1(1), fullpowerMode2(2) } OPTIONAL,
      pusch-TimeDomainAllocationListForMultiPUSCH-r16 [48] EXPLICIT CHOICE {
         release [0] NULL,
         setup [1] EXPLICIT PUSCH-TimeDomainResourceAllocationList-r16
      } OPTIONAL,
      numberOfInvalidSymbolsForDL-UL-Switching-r16 [49] INTEGER (1..4) OPTIONAL
   ]],
   [[
      ul-AccessConfigListDCI-0-2-r17 [50] EXPLICIT CHOICE {
         release [0] NULL,
         setup [1] EXPLICIT UL-AccessConfigListDCI-0-2-r17
      } OPTIONAL,
      betaOffsetsCrossPri0-r17 [51] EXPLICIT CHOICE {
         release [0] NULL,
         setup [1] EXPLICIT BetaOffsetsCrossPriSel-r17
      } OPTIONAL,
      betaOffsetsCrossPri1-r17 [52] EXPLICIT CHOICE {
         release [0] NULL,
         setup [1] EXPLICIT BetaOffsetsCrossPriSel-r17
      } OPTIONAL,
      betaOffsetsCrossPri0DCI-0-2-r17 [53] EXPLICIT CHOICE {
         release [0] NULL,
         setup [1] EXPLICIT BetaOffsetsCrossPriSelDCI-0-2-r17
      } OPTIONAL,
      betaOffsetsCrossPri1DCI-0-2-r17 [54] EXPLICIT CHOICE {
         release [0] NULL,
         setup [1] EXPLICIT BetaOffsetsCrossPriSelDCI-0-2-r17
      } OPTIONAL,
      mappingPattern-r17 [55] ENUMERATED { cyclicMapping(0), 
         sequentialMapping(1) } OPTIONAL,
      secondTPCFieldDCI-0-1-r17 [56] ENUMERATED { enabled(0) } OPTIONAL,
      secondTPCFieldDCI-0-2-r17 [57] ENUMERATED { enabled(0) } OPTIONAL,
      sequenceOffsetForRV-r17 [58] INTEGER (0..3) OPTIONAL,
      ul-AccessConfigListDCI-0-1-r17 [59] EXPLICIT CHOICE {
         release [0] NULL,
         setup [1] EXPLICIT UL-AccessConfigListDCI-0-1-r17
      } OPTIONAL,
      minimumSchedulingOffsetK2-r17 [60] EXPLICIT CHOICE {
         release [0] NULL,
         setup [1] EXPLICIT MinSchedulingOffsetK2-Values-r17
      } OPTIONAL,
      availableSlotCounting-r17 [61] ENUMERATED { enabled(0) } OPTIONAL,
      dmrs-BundlingPUSCH-Config-r17 [62] EXPLICIT CHOICE {
         release [0] NULL,
         setup [1] EXPLICIT DMRS-BundlingPUSCH-Config-r17
      } OPTIONAL,
      harq-ProcessNumberSizeDCI-0-2-v1700 [63] INTEGER (5) OPTIONAL,
      harq-ProcessNumberSizeDCI-0-1-r17 [64] INTEGER (5) OPTIONAL,
      mpe-ResourcePoolToAddModList-r17 [65] SEQUENCE (SIZE (1..maxMPE-Resources-r17)) OF 
         MPE-Resource-r17 OPTIONAL,
      mpe-ResourcePoolToReleaseList-r17 [66] SEQUENCE (SIZE (1..maxMPE-Resources-r17)) OF 
         MPE-ResourceId-r17 OPTIONAL
   ]]
}

CG-UCI-OnPUSCH ::= CHOICE {
   dynamic [0] SEQUENCE (SIZE (1..4)) OF BetaOffsets,
   semiStatic [1] BetaOffsets
}

CG-SDT-Configuration-r17 ::= SEQUENCE {
   cg-SDT-RetransmissionTimer [0] INTEGER (1..64) OPTIONAL, -- Need R
   sdt-SSB-Subset-r17 [1] EXPLICIT CHOICE {
      shortBitmap-r17 [0] BIT STRING  (SIZE (4)),
      mediumBitmap-r17 [1] BIT STRING  (SIZE (8)),
      longBitmap-r17 [2] BIT STRING  (SIZE (64))
   } OPTIONAL, -- Need S
   sdt-SSB-PerCG-PUSCH-r17 [2] ENUMERATED { oneEighth(0), oneFourth(1), half(2)
      , one(3), two(4), four(5), eight(6), sixteen(7) } OPTIONAL, -- Need M
   sdt-P0-PUSCH-r17 [3] INTEGER (-16..15) OPTIONAL, -- Need M
   sdt-Alpha-r17 [4] ENUMERATED { alpha0(0), alpha04(1), alpha05(2), alpha06(3)
      , alpha07(4), alpha08(5), alpha09(6), alpha1(7) } OPTIONAL, -- Need M
   sdt-DMRS-Ports-r17 [5] EXPLICIT CHOICE {
      dmrsType1-r17 [0] BIT STRING  (SIZE (8)),
      dmrsType2-r17 [1] BIT STRING  (SIZE (12))
   } OPTIONAL, -- Need M
   sdt-NrofDMRS-Sequences-r17 [6] INTEGER (1..2) OPTIONAL -- Need M
}

CG-StartingOffsets-r16 ::= SEQUENCE {
   cg-StartingFullBW-InsideCOT-r16 [0] SEQUENCE (SIZE (1..7)) OF INTEGER (0..6)
       OPTIONAL, -- Need R
   cg-StartingFullBW-OutsideCOT-r16 [1] SEQUENCE (SIZE (1..7)) OF INTEGER (0..6)
       OPTIONAL, -- Need R
   cg-StartingPartialBW-InsideCOT-r16 [2] INTEGER (0..6) OPTIONAL, -- Need R
   cg-StartingPartialBW-OutsideCOT-r16 [3] INTEGER (0..6) OPTIONAL -- Need R
}

CG-COT-Sharing-r16 ::= CHOICE {
   noCOT-Sharing-r16 [0] NULL,
   cot-Sharing-r16 [1] SEQUENCE {
      duration-r16 [0] INTEGER (1..39),
      offset-r16 [1] INTEGER (1..39),
      channelAccessPriority-r16 [2] INTEGER (1..4)
   }
}

-- TAG-CONFIGUREDGRANTCONFIG-STOP
-- TAG-CONFIGUREDGRANTCONFIGINDEX-START
ConfiguredGrantConfigIndex-r16 ::= INTEGER (0..maxNrofConfiguredGrantConfig-1-r16)

BetaOffsetsCrossPriSelCG-r17 ::= CHOICE {
   dynamic-r17 [0] SEQUENCE (SIZE (1..4)) OF BetaOffsetsCrossPri-r17,
   semiStatic-r17 [1] BetaOffsetsCrossPri-r17
}

CG-COT-Sharing-r17 ::= CHOICE {
   noCOT-Sharing-r17 [0] NULL,
   cot-Sharing-r17 [1] SEQUENCE {
      duration-r17 [0] INTEGER (1..319),
      offset-r17 [1] INTEGER (1..319)
   }
}

-- TAG-CONDITIONALRECONFIGURATION-STOP
-- TAG-CONFIGUREDGRANTCONFIG-START
ConfiguredGrantConfig ::= SEQUENCE {
   frequencyHopping [0] ENUMERATED { intraSlot(0), interSlot(1) } OPTIONAL, -- Need S
   cg-DMRS-Configuration [1] DMRS-UplinkConfig,
   mcs-Table [2] ENUMERATED { qam256(0), qam64LowSE(1) } OPTIONAL, -- Need S
   mcs-TableTransformPrecoder [3] ENUMERATED { qam256(0), qam64LowSE(1) }
       OPTIONAL, -- Need S
   uci-OnPUSCH [4] EXPLICIT CHOICE {
      release [0] NULL,
      setup [1] EXPLICIT CG-UCI-OnPUSCH
   } OPTIONAL, -- Need M
   resourceAllocation [5] ENUMERATED { resourceAllocationType0(0), 
      resourceAllocationType1(1), dynamicSwitch(2) },
   rbg-Size [6] ENUMERATED { config2(0) } OPTIONAL, -- Need S
   powerControlLoopToUse [7] ENUMERATED { n0(0), n1(1) },
   p0-PUSCH-Alpha [8] P0-PUSCH-AlphaSetId,
   transformPrecoder [9] ENUMERATED { enabled(0), disabled(1) } OPTIONAL, -- Need S
   nrofHARQ-Processes [10] INTEGER (1..16),
   repK [11] ENUMERATED { n1(0), n2(1), n4(2), n8(3) },
   repK-RV [12] ENUMERATED { s1-0231(0), s2-0303(1), s3-0000(2) } OPTIONAL, -- Need R
   periodicity [13] ENUMERATED { sym2(0), sym7(1), sym1x14(2), sym2x14(3), 
      sym4x14(4), sym5x14(5), sym8x14(6), sym10x14(7), sym16x14(8), sym20x14(9)
      , sym32x14(10), sym40x14(11), sym64x14(12), sym80x14(13), sym128x14(14), 
      sym160x14(15), sym256x14(16), sym320x14(17), sym512x14(18), sym640x14(19)
      , sym1024x14(20), sym1280x14(21), sym2560x14(22), sym5120x14(23), 
      sym6(24), sym1x12(25), sym2x12(26), sym4x12(27), sym5x12(28), sym8x12(29)
      , sym10x12(30), sym16x12(31), sym20x12(32), sym32x12(33), sym40x12(34), 
      sym64x12(35), sym80x12(36), sym128x12(37), sym160x12(38), sym256x12(39), 
      sym320x12(40), sym512x12(41), sym640x12(42), sym1280x12(43), 
      sym2560x12(44) },
   configuredGrantTimer [14] INTEGER (1..64) OPTIONAL, -- Need R
   rrc-ConfiguredUplinkGrant [15] SEQUENCE {
      timeDomainOffset [0] INTEGER (0..5119),
      timeDomainAllocation [1] INTEGER (0..15),
      frequencyDomainAllocation [2] BIT STRING  (SIZE (18)),
      antennaPort [3] INTEGER (0..31),
      dmrs-SeqInitialization [4] INTEGER (0..1) OPTIONAL, -- Need R
      precodingAndNumberOfLayers [5] INTEGER (0..63),
      srs-ResourceIndicator [6] INTEGER (0..15) OPTIONAL, -- Need R
      mcsAndTBS [7] INTEGER (0..31),
      frequencyHoppingOffset [8] INTEGER (1..maxNrofPhysicalResourceBlocks-1) OPTIONAL, -- Need R
      pathlossReferenceIndex [9] INTEGER (0..maxNrofPUSCH-PathlossReferenceRSs-1),
      ...,
      [[
         pusch-RepTypeIndicator-r16 [10] ENUMERATED { pusch-RepTypeA(0), 
            pusch-RepTypeB(1) } OPTIONAL,
         frequencyHoppingPUSCH-RepTypeB-r16 [11] ENUMERATED { 
            interRepetition(0), interSlot(1) } OPTIONAL,
         timeReferenceSFN-r16 [12] ENUMERATED { sfn512(0) } OPTIONAL
      ]],
      [[
         pathlossReferenceIndex2-r17 [13] INTEGER (0..maxNrofPUSCH-PathlossReferenceRSs-1) OPTIONAL,
         srs-ResourceIndicator2-r17 [14] INTEGER (0..15) OPTIONAL,
         precodingAndNumberOfLayers2-r17 [15] INTEGER (0..63) OPTIONAL,
         timeDomainAllocation-v1710 [16] INTEGER (16..63) OPTIONAL,
         timeDomainOffset-r17 [17] INTEGER (0..40959) OPTIONAL,
         cg-SDT-Configuration-r17 [18] CG-SDT-Configuration-r17 OPTIONAL
      ]]
   } OPTIONAL,
   ...,
   [[
      cg-RetransmissionTimer-r16 [16] INTEGER (1..64) OPTIONAL,
      cg-minDFI-Delay-r16 [17] ENUMERATED { sym7(0), sym1x14(1), sym2x14(2), 
         sym3x14(3), sym4x14(4), sym5x14(5), sym6x14(6), sym7x14(7), sym8x14(8)
         , sym9x14(9), sym10x14(10), sym11x14(11), sym12x14(12), sym13x14(13), 
         sym14x14(14), sym15x14(15), sym16x14(16) } OPTIONAL,
      cg-nrofPUSCH-InSlot-r16 [18] INTEGER (1..7) OPTIONAL,
      cg-nrofSlots-r16 [19] INTEGER (1..40) OPTIONAL,
      cg-StartingOffsets-r16 [20] CG-StartingOffsets-r16 OPTIONAL,
      cg-UCI-Multiplexing-r16 [21] ENUMERATED { enabled(0) } OPTIONAL,
      cg-COT-SharingOffset-r16 [22] INTEGER (1..39) OPTIONAL,
      betaOffsetCG-UCI-r16 [23] INTEGER (0..31) OPTIONAL,
      cg-COT-SharingList-r16 [24] SEQUENCE (SIZE (1..1709)) OF CG-COT-Sharing-r16
          OPTIONAL,
      harq-ProcID-Offset-r16 [25] INTEGER (0..15) OPTIONAL,
      harq-ProcID-Offset2-r16 [26] INTEGER (0..15) OPTIONAL,
      configuredGrantConfigIndex-r16 [27] ConfiguredGrantConfigIndex-r16
          OPTIONAL,
      configuredGrantConfigIndexMAC-r16 [28] ConfiguredGrantConfigIndexMAC-r16
          OPTIONAL,
      periodicityExt-r16 [29] INTEGER (1..5120) OPTIONAL,
      startingFromRV0-r16 [30] ENUMERATED { on(0), off(1) } OPTIONAL,
      phy-PriorityIndex-r16 [31] ENUMERATED { p0(0), p1(1) } OPTIONAL,
      autonomousTx-r16 [32] ENUMERATED { enabled(0) } OPTIONAL
   ]],
   [[
      cg-betaOffsetsCrossPri0-r17 [33] EXPLICIT CHOICE {
         release [0] NULL,
         setup [1] EXPLICIT BetaOffsetsCrossPriSelCG-r17
      } OPTIONAL,
      cg-betaOffsetsCrossPri1-r17 [34] EXPLICIT CHOICE {
         release [0] NULL,
         setup [1] EXPLICIT BetaOffsetsCrossPriSelCG-r17
      } OPTIONAL,
      mappingPattern-r17 [35] ENUMERATED { cyclicMapping(0), 
         sequentialMapping(1) } OPTIONAL,
      sequenceOffsetForRV-r17 [36] INTEGER (0..3) OPTIONAL,
      p0-PUSCH-Alpha2-r17 [37] P0-PUSCH-AlphaSetId OPTIONAL,
      powerControlLoopToUse2-r17 [38] ENUMERATED { n0(0), n1(1) } OPTIONAL,
      cg-COT-SharingList-r17 [39] SEQUENCE (SIZE (1..50722)) OF CG-COT-Sharing-r17
          OPTIONAL,
      periodicityExt-r17 [40] INTEGER (1..40960) OPTIONAL,
      repK-v1710 [41] ENUMERATED { n12(0), n16(1), n24(2), n32(3) } OPTIONAL,
      nrofHARQ-Processes-v1700 [42] INTEGER (17..32) OPTIONAL,
      harq-ProcID-Offset2-v1700 [43] INTEGER (16..31) OPTIONAL,
      configuredGrantTimer-v1700 [44] INTEGER (33..288) OPTIONAL,
      cg-minDFI-Delay-v1710 [45] INTEGER (238..3584) OPTIONAL
   ]],
   [[
      harq-ProcID-Offset-v1730 [46] INTEGER (16..31) OPTIONAL,
      cg-nrofSlots-r17 [47] INTEGER (1..320) OPTIONAL
   ]]
}

ConfiguredGrantConfigToAddModList-r16 ::= SEQUENCE (SIZE (1..maxNrofConfiguredGrantConfig-r16)) OF 
   ConfiguredGrantConfig

ConfiguredGrantConfigToReleaseList-r16 ::= SEQUENCE (SIZE (1..maxNrofConfiguredGrantConfig-r16)) OF 
   ConfiguredGrantConfigIndex-r16

BWP-UplinkDedicatedSDT-r17 ::= SEQUENCE {
   pusch-Config-r17 [0] EXPLICIT CHOICE {
      release [0] NULL,
      setup [1] EXPLICIT PUSCH-Config
   } OPTIONAL, -- Need M
   configuredGrantConfigToAddModList-r17 [1] 
      ConfiguredGrantConfigToAddModList-r16 OPTIONAL, -- Need N
   configuredGrantConfigToReleaseList-r17 [2] 
      ConfiguredGrantConfigToReleaseList-r16 OPTIONAL,
   ...
}

-- TAG-CONTROLRESOURCESET-STOP
-- TAG-CONTROLRESOURCESETID-START
ControlResourceSetId ::= INTEGER (0..maxNrofControlResourceSets-1)

-- TAG-TCI-STATE-STOP
-- TAG-TCI-STATEID-START
TCI-StateId ::= INTEGER (0..maxNrofTCI-States-1)

ControlResourceSetId-v1610 ::= INTEGER (maxNrofControlResourceSets..maxNrofControlResourceSets-1-r16)

-- TAG-CONNESTFAILURECONTROL-STOP
-- TAG-CONTROLRESOURCESET-START
ControlResourceSet ::= SEQUENCE {
   controlResourceSetId [0] ControlResourceSetId,
   frequencyDomainResources [1] BIT STRING  (SIZE (45)),
   duration [2] INTEGER (1..maxCoReSetDuration),
   cce-REG-MappingType [3] EXPLICIT CHOICE {
      interleaved [0] SEQUENCE {
         reg-BundleSize [0] ENUMERATED { n2(0), n3(1), n6(2) },
         interleaverSize [1] ENUMERATED { n2(0), n3(1), n6(2) },
         shiftIndex [2] INTEGER (0..maxNrofPhysicalResourceBlocks-1) OPTIONAL -- Need S
      },
      nonInterleaved [1] NULL
   },
   precoderGranularity [4] ENUMERATED { sameAsREG-bundle(0), 
      allContiguousRBs(1) },
   tci-StatesPDCCH-ToAddList [5] SEQUENCE (SIZE (1..maxNrofTCI-StatesPDCCH)) OF TCI-StateId OPTIONAL, -- Cond NotSIB-initialBWP
   tci-StatesPDCCH-ToReleaseList [6] SEQUENCE (SIZE (1..maxNrofTCI-StatesPDCCH)) OF TCI-StateId
       OPTIONAL, -- Cond NotSIB-initialBWP
   tci-PresentInDCI [7] ENUMERATED { enabled(0) } OPTIONAL, -- Need S
   pdcch-DMRS-ScramblingID [8] INTEGER (0..65535) OPTIONAL,
   ...,
   [[
      rb-Offset-r16 [9] INTEGER (0..5) OPTIONAL,
      tci-PresentDCI-1-2-r16 [10] INTEGER (1..3) OPTIONAL,
      coresetPoolIndex-r16 [11] INTEGER (0..1) OPTIONAL,
      controlResourceSetId-v1610 [12] ControlResourceSetId-v1610 OPTIONAL
   ]],
   [[
      followUnifiedTCI-State-r17 [13] ENUMERATED { enabled(0) } OPTIONAL
   ]]
}

-- TAG-SEARCHSPACE-STOP
-- TAG-SEARCHSPACEID-START
SearchSpaceId ::= INTEGER (0..maxNrofSearchSpaces-1)

-- TAG-SDAP-CONFIG-STOP
-- TAG-SEARCHSPACE-START
SearchSpace ::= SEQUENCE {
   searchSpaceId [0] SearchSpaceId,
   controlResourceSetId [1] ControlResourceSetId OPTIONAL, -- Cond SetupOnly
   monitoringSlotPeriodicityAndOffset [2] EXPLICIT CHOICE {
      sl1 [0] NULL,
      sl2 [1] INTEGER (0..1),
      sl4 [2] INTEGER (0..3),
      sl5 [3] INTEGER (0..4),
      sl8 [4] INTEGER (0..7),
      sl10 [5] INTEGER (0..9),
      sl16 [6] INTEGER (0..15),
      sl20 [7] INTEGER (0..19),
      sl40 [8] INTEGER (0..39),
      sl80 [9] INTEGER (0..79),
      sl160 [10] INTEGER (0..159),
      sl320 [11] INTEGER (0..319),
      sl640 [12] INTEGER (0..639),
      sl1280 [13] INTEGER (0..1279),
      sl2560 [14] INTEGER (0..2559)
   } OPTIONAL, -- Cond Setup4
   duration [3] INTEGER (2..2559) OPTIONAL, -- Need S
   monitoringSymbolsWithinSlot [4] BIT STRING  (SIZE (14)) OPTIONAL, -- Cond Setup
   nrofCandidates [5] SEQUENCE {
      aggregationLevel1 [0] ENUMERATED { n0(0), n1(1), n2(2), n3(3), n4(4), 
         n5(5), n6(6), n8(7) },
      aggregationLevel2 [1] ENUMERATED { n0(0), n1(1), n2(2), n3(3), n4(4), 
         n5(5), n6(6), n8(7) },
      aggregationLevel4 [2] ENUMERATED { n0(0), n1(1), n2(2), n3(3), n4(4), 
         n5(5), n6(6), n8(7) },
      aggregationLevel8 [3] ENUMERATED { n0(0), n1(1), n2(2), n3(3), n4(4), 
         n5(5), n6(6), n8(7) },
      aggregationLevel16 [4] ENUMERATED { n0(0), n1(1), n2(2), n3(3), n4(4), 
         n5(5), n6(6), n8(7) }
   } OPTIONAL, -- Cond Setup
   searchSpaceType [6] EXPLICIT CHOICE {
      common [0] SEQUENCE {
         dci-Format0-0-AndFormat1-0 [0] SEQUENCE {

            ...
         } OPTIONAL, -- Need R
         dci-Format2-0 [1] SEQUENCE {
            nrofCandidates-SFI [0] SEQUENCE {
               aggregationLevel1 [0] ENUMERATED { n1(0), n2(1) } OPTIONAL, -- Need R
               aggregationLevel2 [1] ENUMERATED { n1(0), n2(1) } OPTIONAL, -- Need R
               aggregationLevel4 [2] ENUMERATED { n1(0), n2(1) } OPTIONAL, -- Need R
               aggregationLevel8 [3] ENUMERATED { n1(0), n2(1) } OPTIONAL, -- Need R
               aggregationLevel16 [4] ENUMERATED { n1(0), n2(1) } OPTIONAL -- Need R
            },
            ...
         } OPTIONAL, -- Need R
         dci-Format2-1 [2] SEQUENCE {

            ...
         } OPTIONAL, -- Need R
         dci-Format2-2 [3] SEQUENCE {

            ...
         } OPTIONAL, -- Need R
         dci-Format2-3 [4] SEQUENCE {
            dummy1 [0] ENUMERATED { sl1(0), sl2(1), sl4(2), sl5(3), sl8(4), 
               sl10(5), sl16(6), sl20(7) } OPTIONAL, -- Cond Setup
            dummy2 [1] ENUMERATED { n1(0), n2(1) },
            ...
         } OPTIONAL -- Need R
      },
      ue-Specific [1] SEQUENCE {
         dci-Formats [0] ENUMERATED { formats0-0-And-1-0(0), 
            formats0-1-And-1-1(1) },
         ...,
         [[
            dci-Formats-MT-r16 [1] ENUMERATED { formats2-5(0) } OPTIONAL,
            dci-FormatsSL-r16 [2] ENUMERATED { formats0-0-And-1-0(0), 
               formats0-1-And-1-1(1), formats3-0(2), formats3-1(3), 
               formats3-0-And-3-1(4) } OPTIONAL,
            dci-FormatsExt-r16 [3] ENUMERATED { formats0-2-And-1-2(0), 
               formats0-1-And-1-1And-0-2-And-1-2(1) } OPTIONAL
         ]]
      }
   } OPTIONAL -- Cond Setup2
}

-- TAG-RLF-TIMERSANDCONSTANTS-STOP
-- TAG-RNTI-VALUE-START
RNTI-Value ::= INTEGER (0..65535)

INT-ConfigurationPerServingCell ::= SEQUENCE {
   servingCellId [0] ServCellIndex,
   positionInDCI [1] INTEGER (0..maxINT-DCI-PayloadSize-1)
}

-- TAG-DOWNLINKCONFIGCOMMONSIB-STOP
-- TAG-DOWNLINKPREEMPTION-START
DownlinkPreemption ::= SEQUENCE {
   int-RNTI [0] RNTI-Value,
   timeFrequencySet [1] ENUMERATED { set0(0), set1(1) },
   dci-PayloadSize [2] INTEGER (0..maxINT-DCI-PayloadSize),
   int-ConfigurationPerServingCell [3] SEQUENCE (SIZE (1..maxNrofServingCells)) OF 
      INT-ConfigurationPerServingCell,
   ...
}

-- TAG-PUSCH-TIMEDOMAINRESOURCEALLOCATIONLIST-STOP
-- TAG-PUSCH-TPC-COMMANDCONFIG-START
PUSCH-TPC-CommandConfig ::= SEQUENCE {
   tpc-Index [0] INTEGER (1..15) OPTIONAL, -- Cond SUL
   tpc-IndexSUL [1] INTEGER (1..15) OPTIONAL, -- Cond SUL-Only
   targetCell [2] ServCellIndex OPTIONAL,
   ...
}

-- TAG-PUCCH-SPATIALRELATIONINFO-STOP
-- TAG-PUCCH-TPC-COMMANDCONFIG-START
PUCCH-TPC-CommandConfig ::= SEQUENCE {
   tpc-IndexPCell [0] INTEGER (1..15) OPTIONAL, -- Cond PDCCH-OfSpcell
   tpc-IndexPUCCH-SCell [1] INTEGER (1..15) OPTIONAL,
   ...,
   [[
      tpc-IndexPUCCH-sSCell-r17 [2] INTEGER (1..15) OPTIONAL,
      tpc-IndexPUCCH-sScellSecondaryPUCCHgroup-r17 [3] INTEGER (1..15) OPTIONAL
   ]]
}

-- TAG-SRS-RSRP-RANGE-STOP
-- TAG-SRS-TPC-COMMANDCONFIG-START
SRS-TPC-CommandConfig ::= SEQUENCE {
   startingBitOfFormat2-3 [0] INTEGER (1..31) OPTIONAL, -- Need R
   fieldTypeFormat2-3 [1] INTEGER (0..1) OPTIONAL,
   ...,
   [[
      startingBitOfFormat2-3SUL [2] INTEGER (1..31) OPTIONAL
   ]]
}

ControlResourceSetId-r16 ::= INTEGER (0..maxNrofControlResourceSets-1-r16)

SearchSpaceExt-r16 ::= SEQUENCE {
   controlResourceSetId-r16 [0] ControlResourceSetId-r16 OPTIONAL, -- Cond SetupOnly2
   searchSpaceType-r16 [1] SEQUENCE {
      common-r16 [0] SEQUENCE {
         dci-Format2-4-r16 [0] SEQUENCE {
            nrofCandidates-CI-r16 [0] SEQUENCE {
               aggregationLevel1-r16 [0] ENUMERATED { n1(0), n2(1) } OPTIONAL, -- Need R
               aggregationLevel2-r16 [1] ENUMERATED { n1(0), n2(1) } OPTIONAL, -- Need R
               aggregationLevel4-r16 [2] ENUMERATED { n1(0), n2(1) } OPTIONAL, -- Need R
               aggregationLevel8-r16 [3] ENUMERATED { n1(0), n2(1) } OPTIONAL, -- Need R
               aggregationLevel16-r16 [4] ENUMERATED { n1(0), n2(1) } OPTIONAL -- Need R
            },
            ...
         } OPTIONAL, -- Need R
         dci-Format2-5-r16 [1] SEQUENCE {
            nrofCandidates-IAB-r16 [0] SEQUENCE {
               aggregationLevel1-r16 [0] ENUMERATED { n1(0), n2(1) } OPTIONAL, -- Need R
               aggregationLevel2-r16 [1] ENUMERATED { n1(0), n2(1) } OPTIONAL, -- Need R
               aggregationLevel4-r16 [2] ENUMERATED { n1(0), n2(1) } OPTIONAL, -- Need R
               aggregationLevel8-r16 [3] ENUMERATED { n1(0), n2(1) } OPTIONAL, -- Need R
               aggregationLevel16-r16 [4] ENUMERATED { n1(0), n2(1) } OPTIONAL -- Need R
            },
            ...
         } OPTIONAL, -- Need R
         dci-Format2-6-r16 [2] SEQUENCE {

            ...
         } OPTIONAL,
         ...
      }
   } OPTIONAL, -- Cond Setup3
   searchSpaceGroupIdList-r16 [2] SEQUENCE (SIZE (1..2)) OF INTEGER (0..1) OPTIONAL
      , -- Need R
   freqMonitorLocations-r16 [3] BIT STRING  (SIZE (5)) OPTIONAL -- Need R
}

CI-ConfigurationPerServingCell-r16 ::= SEQUENCE {
   servingCellId [0] ServCellIndex,
   positionInDCI-r16 [1] INTEGER (0..maxCI-DCI-PayloadSize-1-r16),
   positionInDCI-ForSUL-r16 [2] INTEGER (0..maxCI-DCI-PayloadSize-1-r16) OPTIONAL, -- Cond SUL-Only
   ci-PayloadSize-r16 [3] ENUMERATED { n1(0), n2(1), n4(2), n5(3), n7(4), n8(5)
      , n10(6), n14(7), n16(8), n20(9), n28(10), n32(11), n35(12), n42(13), 
      n56(14), n112(15) },
   timeFrequencyRegion-r16 [4] SEQUENCE {
      timeDurationForCI-r16 [0] ENUMERATED { n2(0), n4(1), n7(2), n14(3) }
          OPTIONAL, -- Cond SymbolPeriodicity
      timeGranularityForCI-r16 [1] ENUMERATED { n1(0), n2(1), n4(2), n7(3), 
         n14(4), n28(5) },
      frequencyRegionForCI-r16 [2] INTEGER (0..37949),
      deltaOffset-r16 [3] INTEGER (0..2),
      ...
   },
   uplinkCancellationPriority-v1610 [5] ENUMERATED { enabled(0) } OPTIONAL -- Need S
}

-- TAG-UL-GAPFR2-CONFIG-STOP
-- TAG-UPLINKCANCELLATION-START
UplinkCancellation-r16 ::= SEQUENCE {
   ci-RNTI-r16 [0] RNTI-Value,
   dci-PayloadSizeForCI-r16 [1] INTEGER (0..maxCI-DCI-PayloadSize-r16),
   ci-ConfigurationPerServingCell-r16 [2] SEQUENCE (SIZE (1..maxNrofServingCells)) OF 
      CI-ConfigurationPerServingCell-r16,
   ...
}

CellGroupForSwitch-r16 ::= SEQUENCE (SIZE (1..16)) OF ServCellIndex

SearchSpaceSwitchConfig-r16 ::= SEQUENCE {
   cellGroupsForSwitchList-r16 [0] SEQUENCE (SIZE (1..4)) OF 
      CellGroupForSwitch-r16 OPTIONAL, -- Need R
   searchSpaceSwitchDelay-r16 [1] INTEGER (10..52) OPTIONAL -- Need R
}

SearchSpaceExt-v1700 ::= SEQUENCE {
   monitoringSlotPeriodicityAndOffset-v1710 [0] EXPLICIT CHOICE {
      sl32 [0] INTEGER (0..31),
      sl64 [1] INTEGER (0..63),
      sl128 [2] INTEGER (0..127),
      sl5120 [3] INTEGER (0..5119),
      sl10240 [4] INTEGER (0..10239),
      sl20480 [5] INTEGER (0..20479)
   } OPTIONAL, -- Cond Setup5
   monitoringSlotsWithinSlotGroup-r17 [1] EXPLICIT CHOICE {
      slotGroupLength4-r17 [0] BIT STRING  (SIZE (4)),
      slotGroupLength8-r17 [1] BIT STRING  (SIZE (8))
   } OPTIONAL, -- Need R
   duration-r17 [2] INTEGER (4..20476) OPTIONAL, -- Need R
   searchSpaceType-r17 [3] SEQUENCE {
      common-r17 [0] SEQUENCE {
         dci-Format4-0-r17 [0] SEQUENCE {

            ...
         } OPTIONAL, -- Need R
         dci-Format4-1-r17 [1] SEQUENCE {

            ...
         } OPTIONAL, -- Need R
         dci-Format4-2-r17 [2] SEQUENCE {

            ...
         } OPTIONAL, -- Need R
         dci-Format4-1-AndFormat4-2-r17 [3] SEQUENCE {

            ...
         } OPTIONAL, -- Need R
         dci-Format2-7-r17 [4] SEQUENCE {
            nrofCandidates-PEI-r17 [0] SEQUENCE {
               aggregationLevel4-r17 [0] ENUMERATED { n0(0), n1(1), n2(2), 
                  n3(3), n4(4) } OPTIONAL, -- Need R
               aggregationLevel8-r17 [1] ENUMERATED { n0(0), n1(1), n2(2) }
                   OPTIONAL, -- Need R
               aggregationLevel16-r17 [2] ENUMERATED { n0(0), n1(1) } OPTIONAL -- Need R
            },
            ...
         } OPTIONAL -- Need R
      }
   } OPTIONAL, -- Need R
   searchSpaceGroupIdList-r17 [4] SEQUENCE (SIZE (1..3)) OF INTEGER (0..maxNrofSearchSpaceGroups-1-r17) OPTIONAL
      , -- Cond DedicatedOnly
   searchSpaceLinkingId-r17 [5] INTEGER (0..maxNrofSearchSpacesLinks-1-r17) OPTIONAL -- Cond DedicatedOnly
}

SCS-SpecificDuration-r17 ::= INTEGER (1..166)

SearchSpaceSwitchConfig-r17 ::= SEQUENCE {
   searchSpaceSwitchTimer-r17 [0] SCS-SpecificDuration-r17 OPTIONAL, -- Need R
   searchSpaceSwitchDelay-r17 [1] INTEGER (10..52) OPTIONAL -- Need R
}

-- TAG-PCI-RANGEINDEXLIST-STOP
-- TAG-PDCCH-CONFIG-START
PDCCH-Config ::= SEQUENCE {
   controlResourceSetToAddModList [0] SEQUENCE (SIZE (1..3)) OF 
      ControlResourceSet OPTIONAL, -- Need N
   controlResourceSetToReleaseList [1] SEQUENCE (SIZE (1..3)) OF 
      ControlResourceSetId OPTIONAL, -- Need N
   searchSpacesToAddModList [2] SEQUENCE (SIZE (1..10)) OF SearchSpace OPTIONAL, -- Need N
   searchSpacesToReleaseList [3] SEQUENCE (SIZE (1..10)) OF SearchSpaceId OPTIONAL
      , -- Need N
   downlinkPreemption [4] EXPLICIT CHOICE {
      release [0] NULL,
      setup [1] EXPLICIT DownlinkPreemption
   } OPTIONAL, -- Need M
   tpc-PUSCH [5] EXPLICIT CHOICE {
      release [0] NULL,
      setup [1] EXPLICIT PUSCH-TPC-CommandConfig
   } OPTIONAL, -- Need M
   tpc-PUCCH [6] EXPLICIT CHOICE {
      release [0] NULL,
      setup [1] EXPLICIT PUCCH-TPC-CommandConfig
   } OPTIONAL, -- Need M
   tpc-SRS [7] EXPLICIT CHOICE {
      release [0] NULL,
      setup [1] EXPLICIT SRS-TPC-CommandConfig
   } OPTIONAL,
   ...,
   [[
      controlResourceSetToAddModListSizeExt-v1610 [8] SEQUENCE (SIZE (1..2)) OF 
         ControlResourceSet OPTIONAL,
      controlResourceSetToReleaseListSizeExt-r16 [9] SEQUENCE (SIZE (1..5)) OF 
         ControlResourceSetId-r16 OPTIONAL,
      searchSpacesToAddModListExt-r16 [10] SEQUENCE (SIZE (1..10)) OF 
         SearchSpaceExt-r16 OPTIONAL,
      uplinkCancellation-r16 [11] EXPLICIT CHOICE {
         release [0] NULL,
         setup [1] EXPLICIT UplinkCancellation-r16
      } OPTIONAL,
      monitoringCapabilityConfig-r16 [12] ENUMERATED { 
         r15monitoringcapability(0), r16monitoringcapability(1) } OPTIONAL,
      searchSpaceSwitchConfig-r16 [13] SearchSpaceSwitchConfig-r16 OPTIONAL
   ]],
   [[
      searchSpacesToAddModListExt-v1700 [14] SEQUENCE (SIZE (1..10)) OF 
         SearchSpaceExt-v1700 OPTIONAL,
      monitoringCapabilityConfig-v1710 [15] ENUMERATED { 
         r17monitoringcapability(0) } OPTIONAL,
      searchSpaceSwitchConfig-r17 [16] SearchSpaceSwitchConfig-r17 OPTIONAL,
      pdcch-SkippingDurationList-r17 [17] SEQUENCE (SIZE (1..3)) OF 
         SCS-SpecificDuration-r17 OPTIONAL
   ]]
}

-- TAG-PRB-ID-STOP
-- TAG-PTRS-DOWNLINKCONFIG-START
PTRS-DownlinkConfig ::= SEQUENCE {
   frequencyDensity [0] SEQUENCE (SIZE (2)) OF INTEGER (1..276) OPTIONAL, -- Need S
   timeDensity [1] SEQUENCE (SIZE (3)) OF INTEGER (0..29) OPTIONAL, -- Need S
   epre-Ratio [2] INTEGER (0..3) OPTIONAL, -- Need S
   resourceElementOffset [3] ENUMERATED { offset01(0), offset10(1), offset11(2)
       } OPTIONAL,
   ...,
   [[
      maxNrofPorts-r16 [4] ENUMERATED { n1(0), n2(1) } OPTIONAL
   ]]
}

-- TAG-DMRS-BUNDLINGPUSCH-CONFIG-STOP
-- TAG-DMRS-DOWNLINKCONFIG-START
DMRS-DownlinkConfig ::= SEQUENCE {
   dmrs-Type [0] ENUMERATED { type2(0) } OPTIONAL, -- Need S
   dmrs-AdditionalPosition [1] ENUMERATED { pos0(0), pos1(1), pos3(2) }
       OPTIONAL, -- Need S
   maxLength [2] ENUMERATED { len2(0) } OPTIONAL, -- Need S
   scramblingID0 [3] INTEGER (0..65535) OPTIONAL, -- Need S
   scramblingID1 [4] INTEGER (0..65535) OPTIONAL, -- Need S
   phaseTrackingRS [5] EXPLICIT CHOICE {
      release [0] NULL,
      setup [1] EXPLICIT PTRS-DownlinkConfig
   } OPTIONAL,
   ...,
   [[
      dmrs-Downlink-r16 [6] ENUMERATED { enabled(0) } OPTIONAL
   ]]
}

-- TAG-BWP-DOWNLINKDEDICATED-STOP
-- TAG-BWP-ID-START
BWP-Id ::= INTEGER (0..maxNrofBWPs)

QCL-Info ::= SEQUENCE {
   cell [0] ServCellIndex OPTIONAL, -- Need R
   bwp-Id [1] BWP-Id OPTIONAL, -- Cond CSI-RS-Indicated
   referenceSignal [2] EXPLICIT CHOICE {
      csi-rs [0] NZP-CSI-RS-ResourceId,
      ssb [1] SSB-Index
   },
   qcl-Type [3] ENUMERATED { typeA(0), typeB(1), typeC(2), typeD(3) },
   ...
}

-- TAG-PATHLOSSREFERENCERS-STOP
-- TAG-PATHLOSSREFERENCERS-ID-START
PathlossReferenceRS-Id-r17 ::= INTEGER (0..maxNrofPathlossReferenceRSs-1-r17)

Uplink-powerControlId-r17 ::= INTEGER (1..maxUL-TCI-r17)

-- TAG-TCI-ACTIVATEDCONFIG-STOP
-- TAG-TCI-STATE-START
TCI-State ::= SEQUENCE {
   tci-StateId [0] TCI-StateId,
   qcl-Type1 [1] QCL-Info,
   qcl-Type2 [2] QCL-Info OPTIONAL,
   ...,
   [[
      additionalPCI-r17 [3] AdditionalPCIIndex-r17 OPTIONAL,
      pathlossReferenceRS-Id-r17 [4] PathlossReferenceRS-Id-r17 OPTIONAL,
      ul-powerControl-r17 [5] Uplink-powerControlId-r17 OPTIONAL
   ]]
}

PDSCH-TimeDomainResourceAllocation ::= SEQUENCE {
   k0 [0] INTEGER (0..32) OPTIONAL, -- Need S
   mappingType [1] ENUMERATED { typeA(0), typeB(1) },
   startSymbolAndLength [2] INTEGER (0..127)
}

-- TAG-PDSCH-SERVINGCELLCONFIG-STOP
-- TAG-PDSCH-TIMEDOMAINRESOURCEALLOCATIONLIST-START
PDSCH-TimeDomainResourceAllocationList ::= SEQUENCE (SIZE (1..maxNrofDL-Allocations)) OF 
   PDSCH-TimeDomainResourceAllocation

-- TAG-RATEMATCHPATTERN-STOP
-- TAG-RATEMATCHPATTERNID-START
RateMatchPatternId ::= INTEGER (0..maxNrofRateMatchPatterns-1)

-- TAG-SS-RSSI-MEASUREMENT-STOP
-- TAG-SUBCARRIERSPACING-START
SubcarrierSpacing ::= ENUMERATED { kHz15(0), kHz30(1), kHz60(2), kHz120(3), 
   kHz240(4), kHz480-v1700(5), kHz960-v1700(6), spare1(7) }

-- TAG-RAN-AREACODE-STOP
-- TAG-RATEMATCHPATTERN-START
RateMatchPattern ::= SEQUENCE {
   rateMatchPatternId [0] RateMatchPatternId,
   patternType [1] EXPLICIT CHOICE {
      bitmaps [0] SEQUENCE {
         resourceBlocks [0] BIT STRING  (SIZE (275)),
         symbolsInResourceBlock [1] EXPLICIT CHOICE {
            oneSlot [0] BIT STRING  (SIZE (14)),
            twoSlots [1] BIT STRING  (SIZE (28))
         },
         periodicityAndPattern [2] EXPLICIT CHOICE {
            n2 [0] BIT STRING  (SIZE (2)),
            n4 [1] BIT STRING  (SIZE (4)),
            n5 [2] BIT STRING  (SIZE (5)),
            n8 [3] BIT STRING  (SIZE (8)),
            n10 [4] BIT STRING  (SIZE (10)),
            n20 [5] BIT STRING  (SIZE (20)),
            n40 [6] BIT STRING  (SIZE (40))
         } OPTIONAL,
         ...
      },
      controlResourceSet [1] ControlResourceSetId
   },
   subcarrierSpacing [2] SubcarrierSpacing OPTIONAL, -- Cond CellLevel
   dummy [3] ENUMERATED { dynamic(0), semiStatic(1) },
   ...,
   [[
      controlResourceSet-r16 [4] ControlResourceSetId-r16 OPTIONAL
   ]]
}

RateMatchPatternGroup ::= SEQUENCE (SIZE (1..maxNrofRateMatchPatternsPerGroup)) OF CHOICE {
   cellLevel [0] RateMatchPatternId,
   bwpLevel [1] RateMatchPatternId
}

ZP-CSI-RS-ResourceId ::= INTEGER (0..maxNrofZP-CSI-RS-Resources-1)

-- TAG-CSI-APERIODICTRIGGERSTATELIST-STOP
-- TAG-CSI-FREQUENCYOCCUPATION-START
CSI-FrequencyOccupation ::= SEQUENCE {
   startingRB [0] INTEGER (0..maxNrofPhysicalResourceBlocks-1),
   nrofRBs [1] INTEGER (24..maxNrofPhysicalResourceBlocksPlus1),
   ...
}

-- TAG-CSI-RS-RESOURCECONFIGMOBILITY-STOP
-- TAG-CSI-RS-RESOURCEMAPPING-START
CSI-RS-ResourceMapping ::= SEQUENCE {
   frequencyDomainAllocation [0] EXPLICIT CHOICE {
      row1 [0] BIT STRING  (SIZE (4)),
      row2 [1] BIT STRING  (SIZE (12)),
      row4 [2] BIT STRING  (SIZE (3)),
      other [3] BIT STRING  (SIZE (6))
   },
   nrofPorts [1] ENUMERATED { p1(0), p2(1), p4(2), p8(3), p12(4), p16(5), 
      p24(6), p32(7) },
   firstOFDMSymbolInTimeDomain [2] INTEGER (0..13),
   firstOFDMSymbolInTimeDomain2 [3] INTEGER (2..12) OPTIONAL, -- Need R
   cdm-Type [4] ENUMERATED { noCDM(0), fd-CDM2(1), cdm4-FD2-TD2(2), 
      cdm8-FD2-TD4(3) },
   density [5] EXPLICIT CHOICE {
      dot5 [0] ENUMERATED { evenPRBs(0), oddPRBs(1) },
      one [1] NULL,
      three [2] NULL,
      spare [3] NULL
   },
   freqBand [6] CSI-FrequencyOccupation,
   ...
}

-- TAG-CSI-RESOURCECONFIGID-STOP
-- TAG-CSI-RESOURCEPERIODICITYANDOFFSET-START
CSI-ResourcePeriodicityAndOffset ::= CHOICE {
   slots4 [0] INTEGER (0..3),
   slots5 [1] INTEGER (0..4),
   slots8 [2] INTEGER (0..7),
   slots10 [3] INTEGER (0..9),
   slots16 [4] INTEGER (0..15),
   slots20 [5] INTEGER (0..19),
   slots32 [6] INTEGER (0..31),
   slots40 [7] INTEGER (0..39),
   slots64 [8] INTEGER (0..63),
   slots80 [9] INTEGER (0..79),
   slots160 [10] INTEGER (0..159),
   slots320 [11] INTEGER (0..319),
   slots640 [12] INTEGER (0..639)
}

-- TAG-UPLINKTXDIRECTCURRENTTWOCARRIERLIST-STOP
-- TAG-ZP-CSI-RS-RESOURCE-START
ZP-CSI-RS-Resource ::= SEQUENCE {
   zp-CSI-RS-ResourceId [0] ZP-CSI-RS-ResourceId,
   resourceMapping [1] CSI-RS-ResourceMapping,
   periodicityAndOffset [2] EXPLICIT CSI-ResourcePeriodicityAndOffset OPTIONAL,
   ...
}

-- TAG-ZP-CSI-RS-RESOURCESET-STOP
-- TAG-ZP-CSI-RS-RESOURCESETID-START
ZP-CSI-RS-ResourceSetId ::= INTEGER (0..maxNrofZP-CSI-RS-ResourceSets-1)

-- TAG-ZP-CSI-RS-RESOURCE-STOP
-- TAG-ZP-CSI-RS-RESOURCESET-START
ZP-CSI-RS-ResourceSet ::= SEQUENCE {
   zp-CSI-RS-ResourceSetId [0] ZP-CSI-RS-ResourceSetId,
   zp-CSI-RS-ResourceIdList [1] SEQUENCE (SIZE (1..maxNrofZP-CSI-RS-ResourcesPerSet)) OF ZP-CSI-RS-ResourceId,
   ...
}

MaxMIMO-LayersDL-r16 ::= INTEGER (1..8)

MinSchedulingOffsetK0-Values-r16 ::= SEQUENCE (SIZE (1..maxNrOfMinSchedulingOffsetValues-r16)) OF INTEGER (0..maxK0-SchedulingOffset-r16)

PDSCH-TimeDomainResourceAllocation-r16 ::= SEQUENCE {
   k0-r16 [0] INTEGER (0..32) OPTIONAL, -- Need S
   mappingType-r16 [1] ENUMERATED { typeA(0), typeB(1) },
   startSymbolAndLength-r16 [2] INTEGER (0..127),
   repetitionNumber-r16 [3] ENUMERATED { n2(0), n3(1), n4(2), n5(3), n6(4), 
      n7(5), n8(6), n16(7) } OPTIONAL,
   ...,
   [[
      k0-v1710 [4] INTEGER (33..128) OPTIONAL
   ]],
   [[
      repetitionNumber-v1730 [5] ENUMERATED { n2(0), n3(1), n4(2), n5(3), n6(4)
         , n7(5), n8(6), n16(7) } OPTIONAL
   ]]
}

PDSCH-TimeDomainResourceAllocationList-r16 ::= SEQUENCE (SIZE (1..maxNrofDL-Allocations)) OF 
   PDSCH-TimeDomainResourceAllocation-r16

FDM-TDM-r16 ::= SEQUENCE {
   repetitionScheme-r16 [0] ENUMERATED { fdmSchemeA(0), fdmSchemeB(1), 
      tdmSchemeA(2) },
   startingSymbolOffsetK-r16 [1] INTEGER (0..7) OPTIONAL -- Need R
}

SlotBased-r16 ::= SEQUENCE {
   tciMapping-r16 [0] ENUMERATED { cyclicMapping(0), sequentialMapping(1) },
   sequenceOffsetForRV-r16 [1] INTEGER (1..3)
}

-- TAG-REJECTWAITTIME-STOP
-- TAG-REPETITIONSCHEMECONFIG-START
RepetitionSchemeConfig-r16 ::= CHOICE {
   fdm-TDM-r16 [0] EXPLICIT CHOICE {
      release [0] NULL,
      setup [1] EXPLICIT FDM-TDM-r16
   },
   slotBased-r16 [1] EXPLICIT CHOICE {
      release [0] NULL,
      setup [1] EXPLICIT SlotBased-r16
   }
}

SlotBased-v1630 ::= SEQUENCE {
   tciMapping-r16 [0] ENUMERATED { cyclicMapping(0), sequentialMapping(1) },
   sequenceOffsetForRV-r16 [1] INTEGER (0)
}

RepetitionSchemeConfig-v1630 ::= SEQUENCE {
   slotBased-v1630 [0] EXPLICIT CHOICE {
      release [0] NULL,
      setup [1] EXPLICIT SlotBased-v1630
   }
}

-- TAG-SENSORLOCATIONINFO-STOP
-- TAG-SERVINGCELLANDBWP-ID-START
ServingCellAndBWP-Id-r17 ::= SEQUENCE {
   servingcell-r17 [0] ServCellIndex,
   bwp-r17 [1] BWP-Id
}

MultiPDSCH-TDRA-r17 ::= SEQUENCE {
   pdsch-TDRA-List-r17 [0] SEQUENCE (SIZE (1..maxNrofMultiplePDSCHs-r17)) OF 
      PDSCH-TimeDomainResourceAllocation-r16,
   ...
}

Dummy-TDRA-List ::= SEQUENCE (SIZE (1..maxNrofDL-Allocations)) OF MultiPDSCH-TDRA-r17

MinSchedulingOffsetK0-Values-r17 ::= SEQUENCE (SIZE (1..maxNrOfMinSchedulingOffsetValues-r16)) OF INTEGER (0..maxK0-SchedulingOffset-r17)

MultiPDSCH-TDRA-List-r17 ::= SEQUENCE (SIZE (1..maxNrofDL-AllocationsExt-r17)) OF MultiPDSCH-TDRA-r17

-- TAG-PDCP-CONFIG-STOP
-- TAG-PDSCH-CONFIG-START
PDSCH-Config ::= SEQUENCE {
   dataScramblingIdentityPDSCH [0] INTEGER (0..1023) OPTIONAL, -- Need S
   dmrs-DownlinkForPDSCH-MappingTypeA [1] EXPLICIT CHOICE {
      release [0] NULL,
      setup [1] EXPLICIT DMRS-DownlinkConfig
   } OPTIONAL, -- Need M
   dmrs-DownlinkForPDSCH-MappingTypeB [2] EXPLICIT CHOICE {
      release [0] NULL,
      setup [1] EXPLICIT DMRS-DownlinkConfig
   } OPTIONAL, -- Need M
   tci-StatesToAddModList [3] SEQUENCE (SIZE (1..maxNrofTCI-States)) OF TCI-State OPTIONAL, -- Need N
   tci-StatesToReleaseList [4] SEQUENCE (SIZE (1..maxNrofTCI-States)) OF TCI-StateId OPTIONAL, -- Need N
   vrb-ToPRB-Interleaver [5] ENUMERATED { n2(0), n4(1) } OPTIONAL, -- Need S
   resourceAllocation [6] ENUMERATED { resourceAllocationType0(0), 
      resourceAllocationType1(1), dynamicSwitch(2) },
   pdsch-TimeDomainAllocationList [7] EXPLICIT CHOICE {
      release [0] NULL,
      setup [1] EXPLICIT PDSCH-TimeDomainResourceAllocationList
   } OPTIONAL, -- Need M
   pdsch-AggregationFactor [8] ENUMERATED { n2(0), n4(1), n8(2) } OPTIONAL, -- Need S
   rateMatchPatternToAddModList [9] SEQUENCE (SIZE (1..maxNrofRateMatchPatterns)) OF RateMatchPattern
       OPTIONAL, -- Need N
   rateMatchPatternToReleaseList [10] SEQUENCE (SIZE (1..maxNrofRateMatchPatterns)) OF 
      RateMatchPatternId OPTIONAL, -- Need N
   rateMatchPatternGroup1 [11] RateMatchPatternGroup OPTIONAL, -- Need R
   rateMatchPatternGroup2 [12] RateMatchPatternGroup OPTIONAL, -- Need R
   rbg-Size [13] ENUMERATED { config1(0), config2(1) },
   mcs-Table [14] ENUMERATED { qam256(0), qam64LowSE(1) } OPTIONAL, -- Need S
   maxNrofCodeWordsScheduledByDCI [15] ENUMERATED { n1(0), n2(1) } OPTIONAL, -- Need R
   prb-BundlingType [16] EXPLICIT CHOICE {
      staticBundling [0] SEQUENCE {
         bundleSize [0] ENUMERATED { n4(0), wideband(1) } OPTIONAL -- Need S
      },
      dynamicBundling [1] SEQUENCE {
         bundleSizeSet1 [0] ENUMERATED { n4(0), wideband(1), n2-wideband(2), 
            n4-wideband(3) } OPTIONAL, -- Need S
         bundleSizeSet2 [1] ENUMERATED { n4(0), wideband(1) } OPTIONAL -- Need S
      }
   },
   zp-CSI-RS-ResourceToAddModList [17] SEQUENCE (SIZE (1..maxNrofZP-CSI-RS-Resources)) OF 
      ZP-CSI-RS-Resource OPTIONAL,
                                                                                                                             -- Need N
   zp-CSI-RS-ResourceToReleaseList [18] SEQUENCE (SIZE (1..maxNrofZP-CSI-RS-Resources)) OF 
      ZP-CSI-RS-ResourceId OPTIONAL,
                                                                                                                             -- Need N
   aperiodic-ZP-CSI-RS-ResourceSetsToAddModList [19] SEQUENCE (SIZE (1..maxNrofZP-CSI-RS-ResourceSets)) OF 
      ZP-CSI-RS-ResourceSet OPTIONAL,
                                                                                                                             -- Need N
   aperiodic-ZP-CSI-RS-ResourceSetsToReleaseList [20] SEQUENCE (SIZE (1..maxNrofZP-CSI-RS-ResourceSets)) OF 
      ZP-CSI-RS-ResourceSetId OPTIONAL,
                                                                                                                             -- Need N
   sp-ZP-CSI-RS-ResourceSetsToAddModList [21] SEQUENCE (SIZE (1..maxNrofZP-CSI-RS-ResourceSets)) OF 
      ZP-CSI-RS-ResourceSet OPTIONAL,
                                                                                                                             -- Need N
   sp-ZP-CSI-RS-ResourceSetsToReleaseList [22] SEQUENCE (SIZE (1..maxNrofZP-CSI-RS-ResourceSets)) OF 
      ZP-CSI-RS-ResourceSetId OPTIONAL,
                                                                                                                             -- Need N
   p-ZP-CSI-RS-ResourceSet [23] EXPLICIT CHOICE {
      release [0] NULL,
      setup [1] EXPLICIT ZP-CSI-RS-ResourceSet
   } OPTIONAL,
   ...,
   [[
      maxMIMO-Layers-r16 [24] EXPLICIT CHOICE {
         release [0] NULL,
         setup [1] EXPLICIT MaxMIMO-LayersDL-r16
      } OPTIONAL,
      minimumSchedulingOffsetK0-r16 [25] EXPLICIT CHOICE {
         release [0] NULL,
         setup [1] EXPLICIT MinSchedulingOffsetK0-Values-r16
      } OPTIONAL,
      antennaPortsFieldPresenceDCI-1-2-r16 [26] ENUMERATED { enabled(0) }
          OPTIONAL,
      aperiodicZP-CSI-RS-ResourceSetsToAddModListDCI-1-2-r16 [27] SEQUENCE (
         SIZE (1..maxNrofZP-CSI-RS-ResourceSets)) OF ZP-CSI-RS-ResourceSet OPTIONAL,
      aperiodicZP-CSI-RS-ResourceSetsToReleaseListDCI-1-2-r16 [28] SEQUENCE (
         SIZE (1..maxNrofZP-CSI-RS-ResourceSets)) OF ZP-CSI-RS-ResourceSetId OPTIONAL,
      dmrs-DownlinkForPDSCH-MappingTypeA-DCI-1-2-r16 [29] EXPLICIT CHOICE {
         release [0] NULL,
         setup [1] EXPLICIT DMRS-DownlinkConfig
      } OPTIONAL,
      dmrs-DownlinkForPDSCH-MappingTypeB-DCI-1-2-r16 [30] EXPLICIT CHOICE {
         release [0] NULL,
         setup [1] EXPLICIT DMRS-DownlinkConfig
      } OPTIONAL,
      dmrs-SequenceInitializationDCI-1-2-r16 [31] ENUMERATED { enabled(0) }
          OPTIONAL,
      harq-ProcessNumberSizeDCI-1-2-r16 [32] INTEGER (0..4) OPTIONAL,
      mcs-TableDCI-1-2-r16 [33] ENUMERATED { qam256(0), qam64LowSE(1) }
          OPTIONAL,
      numberOfBitsForRV-DCI-1-2-r16 [34] INTEGER (0..2) OPTIONAL,
      pdsch-TimeDomainAllocationListDCI-1-2-r16 [35] EXPLICIT CHOICE {
         release [0] NULL,
         setup [1] EXPLICIT PDSCH-TimeDomainResourceAllocationList-r16
      } OPTIONAL,
      prb-BundlingTypeDCI-1-2-r16 [36] EXPLICIT CHOICE {
         staticBundling-r16 [0] SEQUENCE {
            bundleSize-r16 [0] ENUMERATED { n4(0), wideband(1) } OPTIONAL -- Need S
         },
         dynamicBundling-r16 [1] SEQUENCE {
            bundleSizeSet1-r16 [0] ENUMERATED { n4(0), wideband(1), 
               n2-wideband(2), n4-wideband(3) } OPTIONAL, -- Need S
            bundleSizeSet2-r16 [1] ENUMERATED { n4(0), wideband(1) } OPTIONAL -- Need S
         }
      } OPTIONAL,
      priorityIndicatorDCI-1-2-r16 [37] ENUMERATED { enabled(0) } OPTIONAL,
      rateMatchPatternGroup1DCI-1-2-r16 [38] RateMatchPatternGroup OPTIONAL,
      rateMatchPatternGroup2DCI-1-2-r16 [39] RateMatchPatternGroup OPTIONAL,
      resourceAllocationType1GranularityDCI-1-2-r16 [40] ENUMERATED { n2(0), 
         n4(1), n8(2), n16(3) } OPTIONAL,
      vrb-ToPRB-InterleaverDCI-1-2-r16 [41] ENUMERATED { n2(0), n4(1) }
          OPTIONAL,
      referenceOfSLIVDCI-1-2-r16 [42] ENUMERATED { enabled(0) } OPTIONAL,
      resourceAllocationDCI-1-2-r16 [43] ENUMERATED { 
         resourceAllocationType0(0), resourceAllocationType1(1), 
         dynamicSwitch(2) } OPTIONAL,
      priorityIndicatorDCI-1-1-r16 [44] ENUMERATED { enabled(0) } OPTIONAL,
      dataScramblingIdentityPDSCH2-r16 [45] INTEGER (0..1023) OPTIONAL,
      pdsch-TimeDomainAllocationList-r16 [46] EXPLICIT CHOICE {
         release [0] NULL,
         setup [1] EXPLICIT PDSCH-TimeDomainResourceAllocationList-r16
      } OPTIONAL,
      repetitionSchemeConfig-r16 [47] EXPLICIT CHOICE {
         release [0] NULL,
         setup [1] EXPLICIT RepetitionSchemeConfig-r16
      } OPTIONAL
   ]],
   [[
      repetitionSchemeConfig-v1630 [48] EXPLICIT CHOICE {
         release [0] NULL,
         setup [1] EXPLICIT RepetitionSchemeConfig-v1630
      } OPTIONAL
   ]],
   [[
      pdsch-HARQ-ACK-OneShotFeedbackDCI-1-2-r17 [49] ENUMERATED { enabled(0) }
          OPTIONAL,
      pdsch-HARQ-ACK-EnhType3DCI-1-2-r17 [50] ENUMERATED { enabled(0) }
          OPTIONAL,
      pdsch-HARQ-ACK-EnhType3DCI-Field-1-2-r17 [51] ENUMERATED { enabled(0) }
          OPTIONAL,
      pdsch-HARQ-ACK-RetxDCI-1-2-r17 [52] ENUMERATED { enabled(0) } OPTIONAL,
      pucch-sSCellDynDCI-1-2-r17 [53] ENUMERATED { enabled(0) } OPTIONAL,
      dl-OrJointTCI-StateList-r17 [54] EXPLICIT CHOICE {
         explicitlist [0] SEQUENCE {
            dl-OrJointTCI-StateToAddModList-r17 [0] SEQUENCE (SIZE (1..maxNrofTCI-States)) OF 
               TCI-State OPTIONAL,
                                                                                                                            -- Need N
            dl-OrJointTCI-StateToReleaseList-r17 [1] SEQUENCE (SIZE (1..maxNrofTCI-States)) OF 
               TCI-StateId OPTIONAL
                                                                                                                            -- Need N
         },
         unifiedTCI-StateRef-r17 [1] ServingCellAndBWP-Id-r17
      } OPTIONAL,
      beamAppTime-r17 [55] ENUMERATED { n1(0), n2(1), n4(2), n7(3), n14(4), 
         n28(5), n42(6), n56(7), n70(8), n84(9), n98(10), n112(11), n224(12), 
         n336(13), spare2(14), spare1(15) } OPTIONAL,
      dummy [56] EXPLICIT CHOICE {
         release [0] NULL,
         setup [1] EXPLICIT Dummy-TDRA-List
      } OPTIONAL,
      dmrs-FD-OCC-DisabledForRank1-PDSCH-r17 [57] ENUMERATED { true(0) }
          OPTIONAL,
      minimumSchedulingOffsetK0-r17 [58] EXPLICIT CHOICE {
         release [0] NULL,
         setup [1] EXPLICIT MinSchedulingOffsetK0-Values-r17
      } OPTIONAL,
      harq-ProcessNumberSizeDCI-1-2-v1700 [59] INTEGER (0..5) OPTIONAL,
      harq-ProcessNumberSizeDCI-1-1-r17 [60] INTEGER (5) OPTIONAL,
      mcs-Table-r17 [61] ENUMERATED { qam1024(0) } OPTIONAL,
      mcs-TableDCI-1-2-r17 [62] ENUMERATED { qam1024(0) } OPTIONAL,
      xOverheadMulticast-r17 [63] ENUMERATED { xOh6(0), xOh12(1), xOh18(2) }
          OPTIONAL,
      priorityIndicatorDCI-4-2-r17 [64] ENUMERATED { enabled(0) } OPTIONAL,
      sizeDCI-4-2-r17 [65] INTEGER (20..maxDCI-4-2-Size-r17) OPTIONAL
   ]],
   [[
      pdsch-TimeDomainAllocationListForMultiPDSCH-r17 [66] EXPLICIT CHOICE {
         release [0] NULL,
         setup [1] EXPLICIT MultiPDSCH-TDRA-List-r17
      } OPTIONAL
   ]]
}

BWP-DownlinkDedicatedSDT-r17 ::= SEQUENCE {
   pdcch-Config-r17 [0] EXPLICIT CHOICE {
      release [0] NULL,
      setup [1] EXPLICIT PDCCH-Config
   } OPTIONAL, -- Need M
   pdsch-Config-r17 [1] EXPLICIT CHOICE {
      release [0] NULL,
      setup [1] EXPLICIT PDSCH-Config
   } OPTIONAL,
   ...
}

-- TAG-TRESELECTION-STOP
-- TAG-TIMEALIGNMENTTIMER-START
TimeAlignmentTimer ::= ENUMERATED { ms500(0), ms750(1), ms1280(2), ms1920(3), 
   ms2560(4), ms5120(5), ms10240(6), infinity(7) }

-- TAG-RNTI-VALUE-STOP
-- TAG-RSRP-RANGE-START
RSRP-Range ::= INTEGER (0..127)

CG-SDT-TA-ValidationConfig-r17 ::= SEQUENCE {
   cg-SDT-RSRP-ChangeThreshold-r17 [0] ENUMERATED { dB2(0), dB4(1), dB6(2), 
      dB8(3), dB10(4), dB14(5), dB18(6), dB22(7), dB26(8), dB30(9), dB34(10), 
      spare5(11), spare4(12), spare3(13), spare2(14), spare1(15) }
}

SDT-MAC-PHY-CG-Config-r17 ::= SEQUENCE {
     -- CG-SDT specific configuration
   cg-SDT-ConfigLCH-RestrictionToAddModList-r17 [0] SEQUENCE (SIZE (1..maxLC-ID)) OF 
      CG-SDT-ConfigLCH-Restriction-r17 OPTIONAL, -- Need N
   cg-SDT-ConfigLCH-RestrictionToReleaseList-r17 [1] SEQUENCE (SIZE (1..maxLC-ID)) OF 
      LogicalChannelIdentity OPTIONAL, -- Need N
   cg-SDT-ConfigInitialBWP-NUL-r17 [2] EXPLICIT CHOICE {
      release [0] NULL,
      setup [1] EXPLICIT BWP-UplinkDedicatedSDT-r17
   } OPTIONAL, -- Need M
   cg-SDT-ConfigInitialBWP-SUL-r17 [3] EXPLICIT CHOICE {
      release [0] NULL,
      setup [1] EXPLICIT BWP-UplinkDedicatedSDT-r17
   } OPTIONAL, -- Need M
   cg-SDT-ConfigInitialBWP-DL-r17 [4] BWP-DownlinkDedicatedSDT-r17 OPTIONAL, -- Need M
   cg-SDT-TimeAlignmentTimer-r17 [5] TimeAlignmentTimer OPTIONAL, -- Need M
   cg-SDT-RSRP-ThresholdSSB-r17 [6] RSRP-Range OPTIONAL, -- Need M
   cg-SDT-TA-ValidationConfig-r17 [7] EXPLICIT CHOICE {
      release [0] NULL,
      setup [1] EXPLICIT CG-SDT-TA-ValidationConfig-r17
   } OPTIONAL, -- Need M
   cg-SDT-CS-RNTI-r17 [8] RNTI-Value OPTIONAL,
   ...
}

SDT-CG-Config-r17 ::= OCTET STRING (CONTAINING SDT-MAC-PHY-CG-Config-r17)

SRS-PosResourceSetId-r16 ::= INTEGER (0..maxNrofSRS-PosResourceSets-1-r16)

SRS-PosResourceId-r16 ::= INTEGER (0..maxNrofSRS-PosResources-1-r16)

-- TAG-PHR-CONFIG-STOP
-- TAG-PHYSCELLID-START
PhysCellId ::= INTEGER (0..1007)

-- TAG-ARFCN-VALUEEUTRA-STOP
-- TAG-ARFCN-VALUENR-START
ARFCN-ValueNR ::= INTEGER (0..maxNARFCN)

SSB-Configuration-r16 ::= SEQUENCE {
   ssb-Freq-r16 [0] ARFCN-ValueNR,
   halfFrameIndex-r16 [1] ENUMERATED { zero(0), one(1) },
   ssbSubcarrierSpacing-r16 [2] SubcarrierSpacing,
   ssb-Periodicity-r16 [3] ENUMERATED { ms5(0), ms10(1), ms20(2), ms40(3), 
      ms80(4), ms160(5), spare2(6), spare1(7) } OPTIONAL, -- Need S
   sfn0-Offset-r16 [4] SEQUENCE {
      sfn-Offset-r16 [0] INTEGER (0..1023),
      integerSubframeOffset-r16 [1] INTEGER (0..9) OPTIONAL -- Need R
   } OPTIONAL, -- Need R
   sfn-SSB-Offset-r16 [5] INTEGER (0..15),
   ss-PBCH-BlockPower-r16 [6] INTEGER (-60..50) OPTIONAL -- Cond Pathloss
}

SSB-InfoNcell-r16 ::= SEQUENCE {
   physicalCellId-r16 [0] PhysCellId,
   ssb-IndexNcell-r16 [1] SSB-Index OPTIONAL, -- Need S
   ssb-Configuration-r16 [2] SSB-Configuration-r16 OPTIONAL -- Need S
}

DL-PRS-Info-r16 ::= SEQUENCE {
   dl-PRS-ID-r16 [0] INTEGER (0..255),
   dl-PRS-ResourceSetId-r16 [1] INTEGER (0..7),
   dl-PRS-ResourceId-r16 [2] INTEGER (0..63) OPTIONAL -- Need S
}

SRS-PosResourceSet-r16 ::= SEQUENCE {
   srs-PosResourceSetId-r16 [0] SRS-PosResourceSetId-r16,
   srs-PosResourceIdList-r16 [1] SEQUENCE (SIZE (1..maxNrofSRS-ResourcesPerSet)) OF SRS-PosResourceId-r16
       OPTIONAL,
                                                                                                                      -- Cond Setup
   resourceType-r16 [2] EXPLICIT CHOICE {
      aperiodic-r16 [0] SEQUENCE {
         aperiodicSRS-ResourceTriggerList-r16 [0] SEQUENCE (SIZE (1..maxNrofSRS-TriggerStates-1)) OF 
            INTEGER (1..maxNrofSRS-TriggerStates-1) OPTIONAL,
         ...
      },
      semi-persistent-r16 [1] SEQUENCE {

         ...
      },
      periodic-r16 [2] SEQUENCE {

         ...
      }
   },
   alpha-r16 [3] Alpha OPTIONAL, -- Need S
   p0-r16 [4] INTEGER (-202..24) OPTIONAL, -- Cond Setup
   pathlossReferenceRS-Pos-r16 [5] EXPLICIT CHOICE {
      ssb-IndexServing-r16 [0] SSB-Index,
      ssb-Ncell-r16 [1] SSB-InfoNcell-r16,
      dl-PRS-r16 [2] DL-PRS-Info-r16
   } OPTIONAL,
   ...
}

SRS-PeriodicityAndOffset-r16 ::= CHOICE {
   sl1 [0] NULL,
   sl2 [1] INTEGER (0..1),
   sl4 [2] INTEGER (0..3),
   sl5 [3] INTEGER (0..4),
   sl8 [4] INTEGER (0..7),
   sl10 [5] INTEGER (0..9),
   sl16 [6] INTEGER (0..15),
   sl20 [7] INTEGER (0..19),
   sl32 [8] INTEGER (0..31),
   sl40 [9] INTEGER (0..39),
   sl64 [10] INTEGER (0..63),
   sl80 [11] INTEGER (0..79),
   sl160 [12] INTEGER (0..159),
   sl320 [13] INTEGER (0..319),
   sl640 [14] INTEGER (0..639),
   sl1280 [15] INTEGER (0..1279),
   sl2560 [16] INTEGER (0..2559),
   sl5120 [17] INTEGER (0..5119),
   sl10240 [18] INTEGER (0..10239),
   sl40960 [19] INTEGER (0..40959),
   sl81920 [20] INTEGER (0..81919),
   ...
}

SRS-PeriodicityAndOffsetExt-r16 ::= CHOICE {
   sl128 [0] INTEGER (0..127),
   sl256 [1] INTEGER (0..255),
   sl512 [2] INTEGER (0..511),
   sl20480 [3] INTEGER (0..20479)
}

SRS-ResourceId ::= INTEGER (0..maxNrofSRS-Resources-1)

SRS-SpatialRelationInfoPos-r16 ::= CHOICE {
   servingRS-r16 [0] SEQUENCE {
      servingCellId [0] ServCellIndex OPTIONAL, -- Need S
      referenceSignal-r16 [1] EXPLICIT CHOICE {
         ssb-IndexServing-r16 [0] SSB-Index,
         csi-RS-IndexServing-r16 [1] NZP-CSI-RS-ResourceId,
         srs-SpatialRelation-r16 [2] SEQUENCE {
            resourceSelection-r16 [0] EXPLICIT CHOICE {
               srs-ResourceId-r16 [0] SRS-ResourceId,
               srs-PosResourceId-r16 [1] SRS-PosResourceId-r16
            },
            uplinkBWP-r16 [1] BWP-Id
         }
      }
   },
   ssb-Ncell-r16 [1] SSB-InfoNcell-r16,
   dl-PRS-r16 [2] DL-PRS-Info-r16
}

SRS-PosResource-r16 ::= SEQUENCE {
   srs-PosResourceId-r16 [0] SRS-PosResourceId-r16,
   transmissionComb-r16 [1] EXPLICIT CHOICE {
      n2-r16 [0] SEQUENCE {
         combOffset-n2-r16 [0] INTEGER (0..1),
         cyclicShift-n2-r16 [1] INTEGER (0..7)
      },
      n4-r16 [1] SEQUENCE {
         combOffset-n4-r16 [0] INTEGER (0..3),
         cyclicShift-n4-r16 [1] INTEGER (0..11)
      },
      n8-r16 [2] SEQUENCE {
         combOffset-n8-r16 [0] INTEGER (0..7),
         cyclicShift-n8-r16 [1] INTEGER (0..5)
      },
      ...
   },
   resourceMapping-r16 [2] SEQUENCE {
      startPosition-r16 [0] INTEGER (0..13),
      nrofSymbols-r16 [1] ENUMERATED { n1(0), n2(1), n4(2), n8(3), n12(4) }
   },
   freqDomainShift-r16 [3] INTEGER (0..268),
   freqHopping-r16 [4] SEQUENCE {
      c-SRS-r16 [0] INTEGER (0..63),
      ...
   },
   groupOrSequenceHopping-r16 [5] ENUMERATED { neither(0), groupHopping(1), 
      sequenceHopping(2) },
   resourceType-r16 [6] EXPLICIT CHOICE {
      aperiodic-r16 [0] SEQUENCE {
         slotOffset-r16 [0] INTEGER (1..32) OPTIONAL,
         ...
      },
      semi-persistent-r16 [1] SEQUENCE {
         periodicityAndOffset-sp-r16 [0] EXPLICIT SRS-PeriodicityAndOffset-r16,
         ...,
         [[
            periodicityAndOffset-sp-Ext-r16 [1] EXPLICIT 
               SRS-PeriodicityAndOffsetExt-r16 OPTIONAL
         ]]
      },
      periodic-r16 [2] SEQUENCE {
         periodicityAndOffset-p-r16 [0] EXPLICIT SRS-PeriodicityAndOffset-r16,
         ...,
         [[
            periodicityAndOffset-p-Ext-r16 [1] EXPLICIT 
               SRS-PeriodicityAndOffsetExt-r16 OPTIONAL
         ]]
      }
   },
   sequenceId-r16 [7] INTEGER (0..65535),
   spatialRelationInfoPos-r16 [8] EXPLICIT SRS-SpatialRelationInfoPos-r16
       OPTIONAL,
   ...
}

SRS-PosConfig-r17 ::= SEQUENCE {
   srs-PosResourceSetToReleaseList-r17 [0] SEQUENCE (SIZE (1..maxNrofSRS-PosResourceSets-r16)) OF 
      SRS-PosResourceSetId-r16 OPTIONAL, -- Need N
   srs-PosResourceSetToAddModList-r17 [1] SEQUENCE (SIZE (1..maxNrofSRS-PosResourceSets-r16)) OF 
      SRS-PosResourceSet-r16 OPTIONAL, -- Need N
   srs-PosResourceToReleaseList-r17 [2] SEQUENCE (SIZE (1..maxNrofSRS-PosResources-r16)) OF 
      SRS-PosResourceId-r16 OPTIONAL, -- Need N
   srs-PosResourceToAddModList-r17 [3] SEQUENCE (SIZE (1..maxNrofSRS-PosResources-r16)) OF 
      SRS-PosResource-r16 OPTIONAL -- Need N
}

-- TAG-BSR-CONFIG-STOP
-- TAG-BWP-START
BWP ::= SEQUENCE {
   locationAndBandwidth [0] INTEGER (0..37949),
   subcarrierSpacing [1] SubcarrierSpacing,
   cyclicPrefix [2] ENUMERATED { extended(0) } OPTIONAL -- Need R
}

RSRP-ChangeThreshold-r17 ::= ENUMERATED { dB4(0), dB6(1), dB8(2), dB10(3), 
   dB14(4), dB18(5), dB22(6), dB26(7), dB30(8), dB34(9), spare6(10), spare5(11)
   , spare4(12), spare3(13), spare2(14), spare1(15) }

SRS-PosRRC-InactiveConfig-r17 ::= SEQUENCE {
   srs-PosConfigNUL-r17 [0] SRS-PosConfig-r17 OPTIONAL, -- Need R
   srs-PosConfigSUL-r17 [1] SRS-PosConfig-r17 OPTIONAL, -- Need R
   bwp-NUL-r17 [2] BWP OPTIONAL, -- Need S
   bwp-SUL-r17 [3] BWP OPTIONAL, -- Need S
   inactivePosSRS-TimeAlignmentTimer-r17 [4] TimeAlignmentTimer OPTIONAL, -- Need M
   inactivePosSRS-RSRP-ChangeThreshold-r17 [5] RSRP-ChangeThreshold-r17
       OPTIONAL -- Need M
}

SRS-PosRRC-Inactive-r17 ::= OCTET STRING (CONTAINING 
   SRS-PosRRC-InactiveConfig-r17)

EstablishmentCause ::= ENUMERATED { emergency(0), highPriorityAccess(1), 
   mt-Access(2), mo-Signalling(3), mo-Data(4), mo-VoiceCall(5), mo-VideoCall(6)
   , mo-SMS(7), mps-PriorityAccess(8), mcs-PriorityAccess(9), spare6(10), 
   spare5(11), spare4(12), spare3(13), spare2(14), spare1(15) }

UAC-AccessCategory1-SelectionAssistanceInfo ::= ENUMERATED { a(0), b(1), c(2) }
   

UAC-AC1-SelectAssistInfo-r16 ::= ENUMERATED { a(0), b(1), c(2), 
   notConfigured(3) }

FeaturePriority-r17 ::= INTEGER (0..7)

ReducedAggregatedBandwidth ::= ENUMERATED { mhz0(0), mhz10(1), mhz20(2), 
   mhz30(3), mhz40(4), mhz50(5), mhz60(6), mhz80(7), mhz100(8), mhz200(9), 
   mhz300(10), mhz400(11) }

ReducedAggregatedBandwidth-r17 ::= ENUMERATED { mhz0(0), mhz100(1), mhz200(2), 
   mhz400(3), mhz800(4), mhz1200(5), mhz1600(6), mhz2000(7) }

SIB-Type-r17 ::= ENUMERATED { sibType2(0), sibType3(1), sibType4(2), 
   sibType5(3), sibType9(4), sibType10(5), sibType11(6), sibType12(7), 
   sibType13(8), sibType14(9), spare6(10), spare5(11), spare4(12), spare3(13), 
   spare2(14), spare1(15) }

TimeSinceFailure-r16 ::= INTEGER (0..172800)

MCC-MNC-Digit ::= INTEGER (0..9)

MCC ::= SEQUENCE (SIZE (3)) OF MCC-MNC-Digit

MNC ::= SEQUENCE (SIZE (2..3)) OF MCC-MNC-Digit

-- TAG-PHYSICALCELLGROUPCONFIG-STOP
-- TAG-PLMN-IDENTITY-START
PLMN-Identity ::= SEQUENCE {
   mcc [0] MCC OPTIONAL, -- Cond MCC
   mnc [1] MNC
}

-- TAG-CELLGROUPID-STOP
-- TAG-CELLIDENTITY-START
CellIdentity ::= BIT STRING  (SIZE (36))

-- TAG-TDD-UL-DL-CONFIGDEDICATED-STOP
-- TAG-TRACKINGAREACODE-START
TrackingAreaCode ::= BIT STRING  (SIZE (24))

-- TAG-CGI-INFO-NR-STOP
-- TAG-CGI-INFO-LOGGING-START
CGI-Info-Logging-r16 ::= SEQUENCE {
   plmn-Identity-r16 [0] PLMN-Identity,
   cellIdentity-r16 [1] CellIdentity,
   trackingAreaCode-r16 [2] TrackingAreaCode OPTIONAL
}

-- TAG-PCIARFCNEUTRA-STOP
-- TAG-PCIARFCNNR-START
PCI-ARFCN-NR-r16 ::= SEQUENCE {
   physCellId-r16 [0] PhysCellId,
   carrierFreq-r16 [1] ARFCN-ValueNR
}

PLMN-IdentityList-EUTRA-EPC ::= SEQUENCE (SIZE (1..maxPLMN)) OF PLMN-Identity

-- TAG-CELLACCESSRELATEDINFOEUTRA-5GC-STOP
-- TAG-CELLACCESSRELATEDINFOEUTRA-EPC-START
CellAccessRelatedInfo-EUTRA-EPC ::= SEQUENCE {
   plmn-IdentityList-eutra-epc [0] PLMN-IdentityList-EUTRA-EPC,
   trackingAreaCode-eutra-epc [1] BIT STRING  (SIZE (16)),
   cellIdentity-eutra-epc [2] BIT STRING  (SIZE (28))
}

PLMN-Identity-EUTRA-5GC ::= CHOICE {
   plmn-Identity-EUTRA-5GC [0] PLMN-Identity,
   plmn-index [1] INTEGER (1..maxPLMN)
}

PLMN-IdentityList-EUTRA-5GC ::= SEQUENCE (SIZE (1..maxPLMN)) OF PLMN-Identity-EUTRA-5GC
   

-- TAG-RADIOLINKMONITORINGRS-ID-STOP
-- TAG-RAN-AREACODE-START
RAN-AreaCode ::= INTEGER (0..255)

CellIdentity-EUTRA-5GC ::= CHOICE {
   cellIdentity-EUTRA [0] BIT STRING  (SIZE (28)),
   cellId-index [1] INTEGER (1..maxPLMN)
}

-- TAG-CELLACCESSRELATEDINFO-STOP
-- TAG-CELLACCESSRELATEDINFOEUTRA-5GC-START
CellAccessRelatedInfo-EUTRA-5GC ::= SEQUENCE {
   plmn-IdentityList-eutra-5gc [0] PLMN-IdentityList-EUTRA-5GC,
   trackingAreaCode-eutra-5gc [1] TrackingAreaCode,
   ranac-5gc [2] RAN-AreaCode OPTIONAL,
   cellIdentity-eutra-5gc [3] EXPLICIT CellIdentity-EUTRA-5GC
}

-- TAG-FEATURESETUPLINKPERCC-ID-STOP
-- TAG-FREQBANDINDICATOREUTRA-START
FreqBandIndicatorEUTRA ::= INTEGER (1..maxBandsEUTRA)

MultiBandInfoListEUTRA ::= SEQUENCE (SIZE (1..maxMultiBands)) OF FreqBandIndicatorEUTRA

-- TAG-CFR-CONFIGMULTICAST-STOP
-- TAG-CGI-INFOEUTRA-START
CGI-InfoEUTRA ::= SEQUENCE {
   cgi-info-EPC [0] SEQUENCE {
      cgi-info-EPC-legacy [0] CellAccessRelatedInfo-EUTRA-EPC,
      cgi-info-EPC-list [1] SEQUENCE (SIZE (1..maxPLMN)) OF 
         CellAccessRelatedInfo-EUTRA-EPC OPTIONAL
   } OPTIONAL,
   cgi-info-5GC [1] SEQUENCE (SIZE (1..maxPLMN)) OF CellAccessRelatedInfo-EUTRA-5GC
       OPTIONAL,
   freqBandIndicator [2] FreqBandIndicatorEUTRA,
   multiBandInfoList [3] MultiBandInfoListEUTRA OPTIONAL,
   freqBandIndicatorPriority [4] ENUMERATED { true(0) } OPTIONAL
}

-- TAG-EUTRA-NS-PMAXLIST-STOP
-- TAG-EUTRA-PHYSCELLID-START
EUTRA-PhysCellId ::= INTEGER (0..503)

-- TAG-AMF-IDENTIFIER-STOP
-- TAG-ARFCN-VALUEEUTRA-START
ARFCN-ValueEUTRA ::= INTEGER (0..maxEARFCN)

-- TAG-PATHLOSSREFERENCERS-ID-STOP
-- TAG-PCIARFCNEUTRA-START
PCI-ARFCN-EUTRA-r16 ::= SEQUENCE {
   physCellId-r16 [0] EUTRA-PhysCellId,
   carrierFreq-r16 [1] ARFCN-ValueEUTRA
}

-- TAG-CGI-INFOEUTRA-STOP
-- TAG-CGI-INFOEUTRALOGGING-START
CGI-InfoEUTRALogging ::= SEQUENCE {
   plmn-Identity-eutra-5gc [0] PLMN-Identity OPTIONAL,
   trackingAreaCode-eutra-5gc [1] TrackingAreaCode OPTIONAL,
   cellIdentity-eutra-5gc [2] BIT STRING  (SIZE (28)) OPTIONAL,
   plmn-Identity-eutra-epc [3] PLMN-Identity OPTIONAL,
   trackingAreaCode-eutra-epc [4] BIT STRING  (SIZE (16)) OPTIONAL,
   cellIdentity-eutra-epc [5] BIT STRING  (SIZE (28)) OPTIONAL
}

VisitedPSCellInfo-r17 ::= SEQUENCE {
   visitedCellId-r17 [0] EXPLICIT CHOICE {
      nr-CellId-r17 [0] EXPLICIT CHOICE {
         cgi-Info-r17 [0] CGI-Info-Logging-r16,
         pci-arfcn-r17 [1] PCI-ARFCN-NR-r16
      },
      eutra-CellId-r17 [1] EXPLICIT CHOICE {
         cellGlobalId-r17 [0] CGI-InfoEUTRALogging,
         pci-arfcn-r17 [1] PCI-ARFCN-EUTRA-r16
      }
   } OPTIONAL,
   timeSpent-r17 [1] INTEGER (0..4095),
   ...
}

VisitedPSCellInfoList-r17 ::= SEQUENCE (SIZE (1..maxPSCellHistory-r17)) OF VisitedPSCellInfo-r17

VisitedCellInfo-r16 ::= SEQUENCE {
   visitedCellId-r16 [0] EXPLICIT CHOICE {
      nr-CellId-r16 [0] EXPLICIT CHOICE {
         cgi-Info [0] CGI-Info-Logging-r16,
         pci-arfcn-r16 [1] PCI-ARFCN-NR-r16
      },
      eutra-CellId-r16 [1] EXPLICIT CHOICE {
         cellGlobalId-r16 [0] CGI-InfoEUTRA,
         pci-arfcn-r16 [1] PCI-ARFCN-EUTRA-r16
      }
   } OPTIONAL,
   timeSpent-r16 [1] INTEGER (0..4095),
   ...,
   [[
      visitedPSCellInfoListReport-r17 [2] VisitedPSCellInfoList-r17 OPTIONAL
   ]]
}

-- TAG-UTRA-FDD-Q-OFFSETRANGE-STOP
-- TAG-VISITEDCELLINFOLIST-START
VisitedCellInfoList-r16 ::= SEQUENCE (SIZE (1..maxCellHistory-r16)) OF VisitedCellInfo-r16

MobilityHistoryReport-r16 ::= VisitedCellInfoList-r16

TimeUntilReconnection-r16 ::= INTEGER (0..172800)

TimeSinceCHO-Reconfig-r17 ::= INTEGER (0..1023)

TimeConnSourceDAPS-Failure-r17 ::= INTEGER (0..1023)

UPInterruptionTimeAtHO-r17 ::= INTEGER (0..1023)

-- TAG-PUSCH-TPC-COMMANDCONFIG-STOP
-- TAG-Q-OFFSETRANGE-START
Q-OffsetRange ::= ENUMERATED { dB-24(0), dB-22(1), dB-20(2), dB-18(3), dB-16(4)
   , dB-14(5), dB-12(6), dB-10(7), dB-8(8), dB-6(9), dB-5(10), dB-4(11), 
   dB-3(12), dB-2(13), dB-1(14), dB0(15), dB1(16), dB2(17), dB3(18), dB4(19), 
   dB5(20), dB6(21), dB8(22), dB10(23), dB12(24), dB14(25), dB16(26), dB18(27)
   , dB20(28), dB22(29), dB24(30) }

RangeToBestCell ::= Q-OffsetRange

MBS-FSAI-r17 ::= OCTET STRING (SIZE (3))

-- TAG-SIPOS-STOP
-- TAG-ADDITIONALSPECTRUMEMISSION-START
AdditionalSpectrumEmission ::= INTEGER (0..7)

AdditionalSpectrumEmission-v1760 ::= INTEGER (8..39)

-- TAG-ALPHA-STOP
-- TAG-AMF-IDENTIFIER-START
AMF-Identifier ::= BIT STRING  (SIZE (24))

-- TAG-ARFCN-VALUENR-STOP
-- TAG-ARFCN-ValueUTRA-FDD-START
ARFCN-ValueUTRA-FDD-r16 ::= INTEGER (0..16383)

AvailabilityCombinationsPerCellIndex-r16 ::= INTEGER (0..maxNrofDUCells-r16)

AvailabilityCombinationId-r16 ::= INTEGER (0..maxNrofAvailabilityCombinationsPerSet-1-r16)

AI-RNTI-r16 ::= RNTI-Value

-- TAG-BHLOGICALCHANNELIDENTITY-STOP
-- TAG-BHLOGICALCHANNELIDENTITYEXT-START
BH-LogicalChannelIdentity-Ext-r16 ::= INTEGER (320..maxLC-ID-Iab-r16)

-- TAG-BHRLCCHANNELCONFIG-STOP
-- TAG-BHRLCCHANNELID-START
BH-RLC-ChannelID-r16 ::= BIT STRING  (SIZE (16))

NumberOfMsg3-Repetitions-r17 ::= ENUMERATED { n1(0), n2(1), n3(2), n4(3), n7(4)
   , n8(5), n12(6), n16(7) }

-- TAG-RSRP-RANGE-STOP
-- TAG-RSRQ-RANGE-START
RSRQ-Range ::= INTEGER (0..127)

-- TAG-SHORTMAC-I-STOP
-- TAG-SINR-RANGE-START
SINR-Range ::= INTEGER (0..127)

ThresholdNR ::= SEQUENCE {
   thresholdRSRP [0] RSRP-Range OPTIONAL, -- Need R
   thresholdRSRQ [1] RSRQ-Range OPTIONAL, -- Need R
   thresholdSINR [2] SINR-Range OPTIONAL -- Need R
}

-- TAG-MEASTRIGGERQUANTITYEUTRA-STOP
-- TAG-MOBILITYSTATEPARAMETERS-START
MobilityStateParameters ::= SEQUENCE {
   t-Evaluation [0] ENUMERATED { s30(0), s60(1), s120(2), s180(3), s240(4), 
      spare3(5), spare2(6), spare1(7) },
   t-HystNormal [1] ENUMERATED { s30(0), s60(1), s120(2), s180(3), s240(4), 
      spare3(5), spare2(6), spare1(7) },
   n-CellChangeMedium [2] INTEGER (1..16),
   n-CellChangeHigh [3] INTEGER (1..16)
}

-- TAG-REPORTINTERVAL-STOP
-- TAG-RESELECTIONTHRESHOLD-START
ReselectionThreshold ::= INTEGER (0..31)

-- TAG-RESELECTIONTHRESHOLD-STOP
-- TAG-RESELECTIONTHRESHOLDQ-START
ReselectionThresholdQ ::= INTEGER (0..31)

-- TAG-CELLIDENTITY-STOP
-- TAG-CELLRESELECTIONPRIORITY-START
CellReselectionPriority ::= INTEGER (0..7)

-- TAG-CELLRESELECTIONPRIORITY-STOP
-- TAG-CELLRESELECTIONSUBPRIORITY-START
CellReselectionSubPriority ::= ENUMERATED { oDot2(0), oDot4(1), oDot6(2), 
   oDot8(3) }

-- TAG-Q-QUALMIN-STOP
-- TAG-Q-RXLEVMIN-START
Q-RxLevMin ::= INTEGER (-70..-22)

-- TAG-Q-OFFSETRANGE-STOP
-- TAG-Q-QUALMIN-START
Q-QualMin ::= INTEGER (-43..-12)

-- TAG-TRACKINGAREACODE-STOP
-- TAG-TRESELECTION-START
T-Reselection ::= INTEGER (0..7)

-- TAG-FILTERCOEFFICIENT-STOP
-- TAG-FREQBANDINDICATORNR-START
FreqBandIndicatorNR ::= INTEGER (1..1024)

-- TAG-NZP-CSI-RS-RESOURCESETID-STOP
-- TAG-P-MAX-START
P-Max ::= INTEGER (-30..33)

NR-NS-PmaxValue ::= SEQUENCE {
   additionalPmax [0] P-Max OPTIONAL, -- Need N
   additionalSpectrumEmission [1] AdditionalSpectrumEmission
}

-- TAG-NR-DL-PRS-PDC-INFO-STOP
-- TAG-NR-NS-PMAXLIST-START
NR-NS-PmaxList ::= SEQUENCE (SIZE (1..maxNR-NS-Pmax)) OF NR-NS-PmaxValue

NR-MultiBandInfo ::= SEQUENCE {
   freqBandIndicatorNR [0] FreqBandIndicatorNR OPTIONAL, -- Cond OptULNotSIB2
   nr-NS-PmaxList [1] NR-NS-PmaxList OPTIONAL -- Need S
}

-- TAG-MULTIFREQUENCYBANDLISTNR-STOP
-- TAG-MULTIFREQUENCYBANDLISTNR-SIB-START
MultiFrequencyBandListNR-SIB ::= SEQUENCE (SIZE (1..maxNrofMultiBands)) OF NR-MultiBandInfo

-- TAG-SSB-INDEX-STOP
-- TAG-SSB-MTC-START
SSB-MTC ::= SEQUENCE {
   periodicityAndOffset [0] EXPLICIT CHOICE {
      sf5 [0] INTEGER (0..4),
      sf10 [1] INTEGER (0..9),
      sf20 [2] INTEGER (0..19),
      sf40 [3] INTEGER (0..39),
      sf80 [4] INTEGER (0..79),
      sf160 [5] INTEGER (0..159)
   },
   duration [1] ENUMERATED { sf1(0), sf2(1), sf3(2), sf4(3), sf5(4) }
}

-- TAG-SSB-TOMEASURE-STOP
-- TAG-SS-RSSI-MEASUREMENT-START
SS-RSSI-Measurement ::= SEQUENCE {
   measurementSlots [0] BIT STRING  (SIZE (1..80)),
   endSymbol [1] INTEGER (0..3)
}

-- TAG-SSB-POSITIONQCL-RELATION-STOP
-- TAG-SSB-TOMEASURE-START
SSB-ToMeasure ::= CHOICE {
   shortBitmap [0] BIT STRING  (SIZE (4)),
   mediumBitmap [1] BIT STRING  (SIZE (8)),
   longBitmap [2] BIT STRING  (SIZE (64))
}

-- TAG-S-NSSAI-STOP
-- TAG-SPEEDSTATESCALEFACTORS-START
SpeedStateScaleFactors ::= SEQUENCE {
   sf-Medium [0] ENUMERATED { oDot25(0), oDot5(1), oDot75(2), lDot0(3) },
   sf-High [1] ENUMERATED { oDot25(0), oDot5(1), oDot75(2), lDot0(3) }
}

SSB-MTC2-LP-r16 ::= SEQUENCE {
   pci-List [0] SEQUENCE (SIZE (1..maxNrofPCIsPerSMTC)) OF PhysCellId OPTIONAL, -- Need R
   periodicity [1] ENUMERATED { sf10(0), sf20(1), sf40(2), sf80(3), sf160(4), 
      spare3(5), spare2(6), spare1(7) }
}

-- TAG-SSB-MTC-STOP
-- TAG-SSB-POSITIONQCL-RELATION-START
SSB-PositionQCL-Relation-r16 ::= ENUMERATED { n1(0), n2(1), n4(2), n8(3) }

SSB-PositionQCL-Relation-r17 ::= ENUMERATED { n32(0), n64(1) }

SSB-MTC4-r17 ::= SEQUENCE {
   pci-List-r17 [0] SEQUENCE (SIZE (1..maxNrofPCIsPerSMTC)) OF PhysCellId OPTIONAL, -- Need M
   offset-r17 [1] INTEGER (0..159)
}

SSB-MTC4List-r17 ::= SEQUENCE (SIZE (1..3)) OF SSB-MTC4-r17

NR-NS-PmaxValue-v1760 ::= SEQUENCE {
   additionalSpectrumEmission-v1760 [0] AdditionalSpectrumEmission-v1760
       OPTIONAL -- Need N
}

NR-NS-PmaxList-v1760 ::= SEQUENCE (SIZE (1..maxNR-NS-Pmax)) OF NR-NS-PmaxValue-v1760

NR-MultiBandInfo-v1760 ::= SEQUENCE {
   nr-NS-PmaxList-v1760 [0] NR-NS-PmaxList-v1760 OPTIONAL -- Need S
}

MultiFrequencyBandListNR-SIB-v1760 ::= SEQUENCE (SIZE (1..maxNrofMultiBands)) OF 
   NR-MultiBandInfo-v1760

-- TAG-SETUPRELEASE-STOP
-- TAG-SIB2-START
SIB2 ::= SEQUENCE {
   cellReselectionInfoCommon [0] SEQUENCE {
      nrofSS-BlocksToAverage [0] INTEGER (2..maxNrofSS-BlocksToAverage) OPTIONAL, -- Need S
      absThreshSS-BlocksConsolidation [1] ThresholdNR OPTIONAL, -- Need S
      rangeToBestCell [2] RangeToBestCell OPTIONAL, -- Need R
      q-Hyst [3] ENUMERATED { dB0(0), dB1(1), dB2(2), dB3(3), dB4(4), dB5(5), 
         dB6(6), dB8(7), dB10(8), dB12(9), dB14(10), dB16(11), dB18(12), 
         dB20(13), dB22(14), dB24(15) },
      speedStateReselectionPars [4] SEQUENCE {
         mobilityStateParameters [0] MobilityStateParameters,
         q-HystSF [1] SEQUENCE {
            sf-Medium [0] ENUMERATED { dB-6(0), dB-4(1), dB-2(2), dB0(3) },
            sf-High [1] ENUMERATED { dB-6(0), dB-4(1), dB-2(2), dB0(3) }
         }
      } OPTIONAL,
      ...
   },
   cellReselectionServingFreqInfo [1] SEQUENCE {
      s-NonIntraSearchP [0] ReselectionThreshold OPTIONAL, -- Need S
      s-NonIntraSearchQ [1] ReselectionThresholdQ OPTIONAL, -- Need S
      threshServingLowP [2] ReselectionThreshold,
      threshServingLowQ [3] ReselectionThresholdQ OPTIONAL, -- Need R
      cellReselectionPriority [4] CellReselectionPriority,
      cellReselectionSubPriority [5] CellReselectionSubPriority OPTIONAL,
      ...
   },
   intraFreqCellReselectionInfo [2] SEQUENCE {
      q-RxLevMin [0] Q-RxLevMin,
      q-RxLevMinSUL [1] Q-RxLevMin OPTIONAL, -- Need R
      q-QualMin [2] Q-QualMin OPTIONAL, -- Need S
      s-IntraSearchP [3] ReselectionThreshold,
      s-IntraSearchQ [4] ReselectionThresholdQ OPTIONAL, -- Need S
      t-ReselectionNR [5] T-Reselection,
      frequencyBandList [6] MultiFrequencyBandListNR-SIB OPTIONAL, -- Need S
      frequencyBandListSUL [7] MultiFrequencyBandListNR-SIB OPTIONAL, -- Need R
      p-Max [8] P-Max OPTIONAL, -- Need S
      smtc [9] SSB-MTC OPTIONAL, -- Need S
      ss-RSSI-Measurement [10] SS-RSSI-Measurement OPTIONAL, -- Need R
      ssb-ToMeasure [11] EXPLICIT SSB-ToMeasure OPTIONAL, -- Need S
      deriveSSB-IndexFromCell [12] BOOLEAN,
      ...,
      [[
         t-ReselectionNR-SF [13] SpeedStateScaleFactors OPTIONAL
      ]],
      [[
         smtc2-LP-r16 [14] SSB-MTC2-LP-r16 OPTIONAL,
         ssb-PositionQCL-Common-r16 [15] SSB-PositionQCL-Relation-r16 OPTIONAL
      ]],
      [[
         ssb-PositionQCL-Common-r17 [16] SSB-PositionQCL-Relation-r17 OPTIONAL
      ]],
      [[
         smtc4list-r17 [17] SSB-MTC4List-r17 OPTIONAL
      ]],
      [[
         frequencyBandList-v1760 [18] MultiFrequencyBandListNR-SIB-v1760
             OPTIONAL,
         frequencyBandListSUL-v1760 [19] MultiFrequencyBandListNR-SIB-v1760
             OPTIONAL
      ]]
   },
   ...,
   [[
      relaxedMeasurement-r16 [3] SEQUENCE {
         lowMobilityEvaluation-r16 [0] SEQUENCE {
            s-SearchDeltaP-r16 [0] ENUMERATED { dB3(0), dB6(1), dB9(2), dB12(3)
               , dB15(4), spare3(5), spare2(6), spare1(7) },
            t-SearchDeltaP-r16 [1] ENUMERATED { s5(0), s10(1), s20(2), s30(3), 
               s60(4), s120(5), s180(6), s240(7), s300(8), spare7(9), 
               spare6(10), spare5(11), spare4(12), spare3(13), spare2(14), 
               spare1(15) }
         } OPTIONAL, -- Need R
         cellEdgeEvaluation-r16 [1] SEQUENCE {
            s-SearchThresholdP-r16 [0] ReselectionThreshold,
            s-SearchThresholdQ-r16 [1] ReselectionThresholdQ OPTIONAL -- Need R
         } OPTIONAL, -- Need R
         combineRelaxedMeasCondition-r16 [2] ENUMERATED { true(0) } OPTIONAL, -- Need R
         highPriorityMeasRelax-r16 [3] ENUMERATED { true(0) } OPTIONAL -- Need R
      } OPTIONAL
   ]],
   [[
      cellEquivalentSize-r17 [4] INTEGER (2..16) OPTIONAL,
      relaxedMeasurement-r17 [5] SEQUENCE {
         stationaryMobilityEvaluation-r17 [0] SEQUENCE {
            s-SearchDeltaP-Stationary-r17 [0] ENUMERATED { dB2(0), dB3(1), 
               dB6(2), dB9(3), dB12(4), dB15(5), spare2(6), spare1(7) },
            t-SearchDeltaP-Stationary-r17 [1] ENUMERATED { s5(0), s10(1), 
               s20(2), s30(3), s60(4), s120(5), s180(6), s240(7), s300(8), 
               spare7(9), spare6(10), spare5(11), spare4(12), spare3(13), 
               spare2(14), spare1(15) }
         },
         cellEdgeEvaluationWhileStationary-r17 [1] SEQUENCE {
            s-SearchThresholdP2-r17 [0] ReselectionThreshold,
            s-SearchThresholdQ2-r17 [1] ReselectionThresholdQ OPTIONAL -- Need R
         } OPTIONAL, -- Need R
         combineRelaxedMeasCondition2-r17 [2] ENUMERATED { true(0) } OPTIONAL -- Need R
      } OPTIONAL
   ]]
}

IntraFreqNeighCellInfo ::= SEQUENCE {
   physCellId [0] PhysCellId,
   q-OffsetCell [1] Q-OffsetRange,
   q-RxLevMinOffsetCell [2] INTEGER (1..8) OPTIONAL, -- Need R
   q-RxLevMinOffsetCellSUL [3] INTEGER (1..8) OPTIONAL, -- Need R
   q-QualMinOffsetCell [4] INTEGER (1..8) OPTIONAL,
   ...
}

IntraFreqNeighCellList ::= SEQUENCE (SIZE (1..maxCellIntra)) OF IntraFreqNeighCellInfo

-- TAG-PCI-LIST-STOP
-- TAG-PCI-RANGE-START
PCI-Range ::= SEQUENCE {
   start [0] PhysCellId,
   range [1] ENUMERATED { n4(0), n8(1), n12(2), n16(3), n24(4), n32(5), n48(6)
      , n64(7), n84(8), n96(9), n128(10), n168(11), n252(12), n504(13), 
      n1008(14), spare1(15) } OPTIONAL -- Need S
}

IntraFreqExcludedCellList ::= SEQUENCE (SIZE (1..maxCellExcluded)) OF PCI-Range

IntraFreqNeighCellInfo-v1610 ::= SEQUENCE {
   ssb-PositionQCL-r16 [0] SSB-PositionQCL-Relation-r16 OPTIONAL -- Cond SharedSpectrum2
}

IntraFreqNeighCellList-v1610 ::= SEQUENCE (SIZE (1..maxCellIntra)) OF 
   IntraFreqNeighCellInfo-v1610

IntraFreqAllowedCellList-r16 ::= SEQUENCE (SIZE (1..maxCellAllowed)) OF PCI-Range

IntraFreqCAG-CellListPerPLMN-r16 ::= SEQUENCE {
   plmn-IdentityIndex-r16 [0] INTEGER (1..maxPLMN),
   cag-CellList-r16 [1] SEQUENCE (SIZE (1..maxCAG-Cell-r16)) OF PCI-Range
}

IntraFreqNeighHSDN-CellList-r17 ::= SEQUENCE (SIZE (1..maxCellIntra)) OF PCI-Range

IntraFreqNeighCellInfo-v1710 ::= SEQUENCE {
   ssb-PositionQCL-r17 [0] SSB-PositionQCL-Relation-r17 OPTIONAL -- Cond SharedSpectrum2
}

IntraFreqNeighCellList-v1710 ::= SEQUENCE (SIZE (1..maxCellIntra)) OF 
   IntraFreqNeighCellInfo-v1710

-- TAG-SIB2-STOP
-- TAG-SIB3-START
SIB3 ::= SEQUENCE {
   intraFreqNeighCellList [0] IntraFreqNeighCellList OPTIONAL, -- Need R
   intraFreqExcludedCellList [1] IntraFreqExcludedCellList OPTIONAL, -- Need R
   lateNonCriticalExtension [2] OCTET STRING OPTIONAL,
   ...,
   [[
      intraFreqNeighCellList-v1610 [3] IntraFreqNeighCellList-v1610 OPTIONAL,
      intraFreqAllowedCellList-r16 [4] IntraFreqAllowedCellList-r16 OPTIONAL,
      intraFreqCAG-CellList-r16 [5] SEQUENCE (SIZE (1..maxPLMN)) OF 
         IntraFreqCAG-CellListPerPLMN-r16 OPTIONAL
   ]],
   [[
      intraFreqNeighHSDN-CellList-r17 [6] IntraFreqNeighHSDN-CellList-r17
          OPTIONAL,
      intraFreqNeighCellList-v1710 [7] IntraFreqNeighCellList-v1710 OPTIONAL
   ]],
   [[
      channelAccessMode2-r17 [8] ENUMERATED { enabled(0) } OPTIONAL
   ]]
}

InterFreqNeighCellInfo ::= SEQUENCE {
   physCellId [0] PhysCellId,
   q-OffsetCell [1] Q-OffsetRange,
   q-RxLevMinOffsetCell [2] INTEGER (1..8) OPTIONAL, -- Need R
   q-RxLevMinOffsetCellSUL [3] INTEGER (1..8) OPTIONAL, -- Need R
   q-QualMinOffsetCell [4] INTEGER (1..8) OPTIONAL,
   ...
}

InterFreqNeighCellList ::= SEQUENCE (SIZE (1..maxCellInter)) OF InterFreqNeighCellInfo

InterFreqExcludedCellList ::= SEQUENCE (SIZE (1..maxCellExcluded)) OF PCI-Range

InterFreqCarrierFreqInfo ::= SEQUENCE {
   dl-CarrierFreq [0] ARFCN-ValueNR,
   frequencyBandList [1] MultiFrequencyBandListNR-SIB OPTIONAL, -- Cond Mandatory
   frequencyBandListSUL [2] MultiFrequencyBandListNR-SIB OPTIONAL, -- Need R
   nrofSS-BlocksToAverage [3] INTEGER (2..maxNrofSS-BlocksToAverage) OPTIONAL, -- Need S
   absThreshSS-BlocksConsolidation [4] ThresholdNR OPTIONAL, -- Need S
   smtc [5] SSB-MTC OPTIONAL, -- Need S
   ssbSubcarrierSpacing [6] SubcarrierSpacing,
   ssb-ToMeasure [7] EXPLICIT SSB-ToMeasure OPTIONAL, -- Need S
   deriveSSB-IndexFromCell [8] BOOLEAN,
   ss-RSSI-Measurement [9] SS-RSSI-Measurement OPTIONAL, -- Need R
   q-RxLevMin [10] Q-RxLevMin,
   q-RxLevMinSUL [11] Q-RxLevMin OPTIONAL, -- Need R
   q-QualMin [12] Q-QualMin OPTIONAL, -- Need S
   p-Max [13] P-Max OPTIONAL, -- Need S
   t-ReselectionNR [14] T-Reselection,
   t-ReselectionNR-SF [15] SpeedStateScaleFactors OPTIONAL, -- Need S
   threshX-HighP [16] ReselectionThreshold,
   threshX-LowP [17] ReselectionThreshold,
   threshX-Q [18] SEQUENCE {
      threshX-HighQ [0] ReselectionThresholdQ,
      threshX-LowQ [1] ReselectionThresholdQ
   } OPTIONAL, -- Cond RSRQ
   cellReselectionPriority [19] CellReselectionPriority OPTIONAL, -- Need R
   cellReselectionSubPriority [20] CellReselectionSubPriority OPTIONAL, -- Need R
   q-OffsetFreq [21] Q-OffsetRange DEFAULT dB0,
   interFreqNeighCellList [22] InterFreqNeighCellList OPTIONAL, -- Need R
   interFreqExcludedCellList [23] InterFreqExcludedCellList OPTIONAL,
   ...
}

InterFreqCarrierFreqList ::= SEQUENCE (SIZE (1..maxFreq)) OF InterFreqCarrierFreqInfo

InterFreqNeighCellInfo-v1610 ::= SEQUENCE {
   ssb-PositionQCL-r16 [0] SSB-PositionQCL-Relation-r16 OPTIONAL -- Cond SharedSpectrum2
}

InterFreqNeighCellList-v1610 ::= SEQUENCE (SIZE (1..maxCellInter)) OF 
   InterFreqNeighCellInfo-v1610

InterFreqAllowedCellList-r16 ::= SEQUENCE (SIZE (1..maxCellAllowed)) OF PCI-Range

InterFreqCAG-CellListPerPLMN-r16 ::= SEQUENCE {
   plmn-IdentityIndex-r16 [0] INTEGER (1..maxPLMN),
   cag-CellList-r16 [1] SEQUENCE (SIZE (1..maxCAG-Cell-r16)) OF PCI-Range
}

InterFreqCarrierFreqInfo-v1610 ::= SEQUENCE {
   interFreqNeighCellList-v1610 [0] InterFreqNeighCellList-v1610 OPTIONAL, -- Need R
   smtc2-LP-r16 [1] SSB-MTC2-LP-r16 OPTIONAL, -- Need R
   interFreqAllowedCellList-r16 [2] InterFreqAllowedCellList-r16 OPTIONAL, -- Cond SharedSpectrum2
   ssb-PositionQCL-Common-r16 [3] SSB-PositionQCL-Relation-r16 OPTIONAL, -- Cond SharedSpectrum
   interFreqCAG-CellList-r16 [4] SEQUENCE (SIZE (1..maxPLMN)) OF 
      InterFreqCAG-CellListPerPLMN-r16 OPTIONAL -- Need R
}

InterFreqCarrierFreqList-v1610 ::= SEQUENCE (SIZE (1..maxFreq)) OF 
   InterFreqCarrierFreqInfo-v1610

InterFreqNeighHSDN-CellList-r17 ::= SEQUENCE (SIZE (1..maxCellInter)) OF PCI-Range

InterFreqNeighCellInfo-v1710 ::= SEQUENCE {
   ssb-PositionQCL-r17 [0] SSB-PositionQCL-Relation-r17 OPTIONAL -- Cond SharedSpectrum2
}

InterFreqNeighCellList-v1710 ::= SEQUENCE (SIZE (1..maxCellInter)) OF 
   InterFreqNeighCellInfo-v1710

InterFreqCarrierFreqInfo-v1700 ::= SEQUENCE {
   interFreqNeighHSDN-CellList-r17 [0] InterFreqNeighHSDN-CellList-r17 OPTIONAL
      , -- Need R
   highSpeedMeasInterFreq-r17 [1] ENUMERATED { true(0) } OPTIONAL, -- Need R
   redCapAccessAllowed-r17 [2] ENUMERATED { true(0) } OPTIONAL, -- Need R
   ssb-PositionQCL-Common-r17 [3] SSB-PositionQCL-Relation-r17 OPTIONAL, -- Cond SharedSpectrum
   interFreqNeighCellList-v1710 [4] InterFreqNeighCellList-v1710 OPTIONAL -- Cond SharedSpectrum2
}

InterFreqCarrierFreqList-v1700 ::= SEQUENCE (SIZE (1..maxFreq)) OF 
   InterFreqCarrierFreqInfo-v1700

InterFreqCarrierFreqInfo-v1720 ::= SEQUENCE {
   smtc4list-r17 [0] SSB-MTC4List-r17 OPTIONAL -- Need R
}

InterFreqCarrierFreqList-v1720 ::= SEQUENCE (SIZE (1..maxFreq)) OF 
   InterFreqCarrierFreqInfo-v1720

InterFreqCarrierFreqInfo-v1730 ::= SEQUENCE {
   channelAccessMode2-r17 [0] ENUMERATED { enabled(0) } OPTIONAL -- Need R
}

InterFreqCarrierFreqList-v1730 ::= SEQUENCE (SIZE (1..maxFreq)) OF 
   InterFreqCarrierFreqInfo-v1730

InterFreqCarrierFreqInfo-v1760 ::= SEQUENCE {
   frequencyBandList-v1760 [0] MultiFrequencyBandListNR-SIB-v1760 OPTIONAL, -- Need R
   frequencyBandListSUL-v1760 [1] MultiFrequencyBandListNR-SIB-v1760 OPTIONAL -- Need R
}

InterFreqCarrierFreqList-v1760 ::= SEQUENCE (SIZE (1..maxFreq)) OF 
   InterFreqCarrierFreqInfo-v1760

-- TAG-SIB3-STOP
-- TAG-SIB4-START
SIB4 ::= SEQUENCE {
   interFreqCarrierFreqList [0] InterFreqCarrierFreqList,
   lateNonCriticalExtension [1] OCTET STRING OPTIONAL,
   ...,
   [[
      interFreqCarrierFreqList-v1610 [2] InterFreqCarrierFreqList-v1610
          OPTIONAL
   ]],
   [[
      interFreqCarrierFreqList-v1700 [3] InterFreqCarrierFreqList-v1700
          OPTIONAL
   ]],
   [[
      interFreqCarrierFreqList-v1720 [4] InterFreqCarrierFreqList-v1720
          OPTIONAL
   ]],
   [[
      interFreqCarrierFreqList-v1730 [5] InterFreqCarrierFreqList-v1730
          OPTIONAL
   ]],
   [[
      interFreqCarrierFreqList-v1760 [6] InterFreqCarrierFreqList-v1760
          OPTIONAL
   ]]
}

EUTRA-NS-PmaxValue ::= SEQUENCE {
   additionalPmax [0] INTEGER (-30..33) OPTIONAL, -- Need R
   additionalSpectrumEmission [1] INTEGER (1..288) OPTIONAL -- Need R
}

-- TAG-EUTRA-MULTIBANDINFOLIST-STOP
-- TAG-EUTRA-NS-PMAXLIST-START
EUTRA-NS-PmaxList ::= SEQUENCE (SIZE (1..maxEUTRA-NS-Pmax)) OF EUTRA-NS-PmaxValue

EUTRA-MultiBandInfo ::= SEQUENCE {
   eutra-FreqBandIndicator [0] FreqBandIndicatorEUTRA,
   eutra-NS-PmaxList [1] EUTRA-NS-PmaxList OPTIONAL -- Need R
}

-- TAG-EUTRA-MBSFN-SUBFRAMECONFIGLIST-STOP
-- TAG-EUTRA-MULTIBANDINFOLIST-START
EUTRA-MultiBandInfoList ::= SEQUENCE (SIZE (1..maxMultiBands)) OF EUTRA-MultiBandInfo

-- TAG-EUTRA-PRESENCEANTENNAPORT1-STOP
-- TAG-EUTRA-Q-OFFSETRANGE-START
EUTRA-Q-OffsetRange ::= ENUMERATED { dB-24(0), dB-22(1), dB-20(2), dB-18(3), 
   dB-16(4), dB-14(5), dB-12(6), dB-10(7), dB-8(8), dB-6(9), dB-5(10), dB-4(11)
   , dB-3(12), dB-2(13), dB-1(14), dB0(15), dB1(16), dB2(17), dB3(18), dB4(19)
   , dB5(20), dB6(21), dB8(22), dB10(23), dB12(24), dB14(25), dB16(26), 
   dB18(27), dB20(28), dB22(29), dB24(30) }

EUTRA-FreqNeighCellInfo ::= SEQUENCE {
   physCellId [0] EUTRA-PhysCellId,
   dummy [1] EUTRA-Q-OffsetRange,
   q-RxLevMinOffsetCell [2] INTEGER (1..8) OPTIONAL, -- Need R
   q-QualMinOffsetCell [3] INTEGER (1..8) OPTIONAL -- Need R
}

EUTRA-FreqNeighCellList ::= SEQUENCE (SIZE (1..maxCellEUTRA)) OF EUTRA-FreqNeighCellInfo

-- TAG-EUTRA-PHYSCELLID-STOP
-- TAG-EUTRA-PHYSCELLIDRANGE-START
EUTRA-PhysCellIdRange ::= SEQUENCE {
   start [0] EUTRA-PhysCellId,
   range [1] ENUMERATED { n4(0), n8(1), n12(2), n16(3), n24(4), n32(5), n48(6)
      , n64(7), n84(8), n96(9), n128(10), n168(11), n252(12), n504(13), 
      spare2(14), spare1(15) } OPTIONAL -- Need N
}

EUTRA-FreqExcludedCellList ::= SEQUENCE (SIZE (1..maxEUTRA-CellExcluded)) OF EUTRA-PhysCellIdRange

-- TAG-DEDICATEDINFOF1C-STOP
-- TAG-EUTRA-ALLOWEDMEASBANDWIDTH-START
EUTRA-AllowedMeasBandwidth ::= ENUMERATED { mbw6(0), mbw15(1), mbw25(2), 
   mbw50(3), mbw75(4), mbw100(5) }

-- TAG-EUTRA-PHYSCELLIDRANGE-STOP
-- TAG-EUTRA-PRESENCEANTENNAPORT1-START
EUTRA-PresenceAntennaPort1 ::= BOOLEAN

CarrierFreqEUTRA ::= SEQUENCE {
   carrierFreq [0] ARFCN-ValueEUTRA,
   eutra-multiBandInfoList [1] EUTRA-MultiBandInfoList OPTIONAL, -- Need R
   eutra-FreqNeighCellList [2] EUTRA-FreqNeighCellList OPTIONAL, -- Need R
   eutra-ExcludedCellList [3] EUTRA-FreqExcludedCellList OPTIONAL, -- Need R
   allowedMeasBandwidth [4] EUTRA-AllowedMeasBandwidth,
   presenceAntennaPort1 [5] EUTRA-PresenceAntennaPort1,
   cellReselectionPriority [6] CellReselectionPriority OPTIONAL, -- Need R
   cellReselectionSubPriority [7] CellReselectionSubPriority OPTIONAL, -- Need R
   threshX-High [8] ReselectionThreshold,
   threshX-Low [9] ReselectionThreshold,
   q-RxLevMin [10] INTEGER (-70..-22),
   q-QualMin [11] INTEGER (-34..-3),
   p-MaxEUTRA [12] INTEGER (-30..33),
   threshX-Q [13] SEQUENCE {
      threshX-HighQ [0] ReselectionThresholdQ,
      threshX-LowQ [1] ReselectionThresholdQ
   } OPTIONAL -- Cond RSRQ
}

CarrierFreqListEUTRA ::= SEQUENCE (SIZE (1..maxEUTRA-Carrier)) OF CarrierFreqEUTRA

CarrierFreqEUTRA-v1610 ::= SEQUENCE {
   highSpeedEUTRACarrier-r16 [0] ENUMERATED { true(0) } OPTIONAL -- Need R
}

CarrierFreqListEUTRA-v1610 ::= SEQUENCE (SIZE (1..maxEUTRA-Carrier)) OF CarrierFreqEUTRA-v1610

EUTRA-FreqNeighHSDN-CellList-r17 ::= SEQUENCE (SIZE (1..maxCellEUTRA)) OF 
   EUTRA-PhysCellIdRange

CarrierFreqEUTRA-v1700 ::= SEQUENCE {
   eutra-FreqNeighHSDN-CellList-r17 [0] EUTRA-FreqNeighHSDN-CellList-r17
       OPTIONAL -- Need R
}

CarrierFreqListEUTRA-v1700 ::= SEQUENCE (SIZE (1..maxEUTRA-Carrier)) OF CarrierFreqEUTRA-v1700

-- TAG-SIB4-STOP
-- TAG-SIB5-START
SIB5 ::= SEQUENCE {
   carrierFreqListEUTRA [0] CarrierFreqListEUTRA OPTIONAL, -- Need R
   t-ReselectionEUTRA [1] T-Reselection,
   t-ReselectionEUTRA-SF [2] SpeedStateScaleFactors OPTIONAL, -- Need S
   lateNonCriticalExtension [3] OCTET STRING OPTIONAL,
   ...,
   [[
      carrierFreqListEUTRA-v1610 [4] CarrierFreqListEUTRA-v1610 OPTIONAL
   ]],
   [[
      carrierFreqListEUTRA-v1700 [5] CarrierFreqListEUTRA-v1700 OPTIONAL,
      idleModeMeasVoiceFallback-r17 [6] ENUMERATED { true(0) } OPTIONAL
   ]]
}

-- TAG-SIB5-STOP
-- TAG-SIB6-START
SIB6 ::= SEQUENCE {
   messageIdentifier [0] BIT STRING  (SIZE (16)),
   serialNumber [1] BIT STRING  (SIZE (16)),
   warningType [2] OCTET STRING (SIZE (2)),
   lateNonCriticalExtension [3] OCTET STRING OPTIONAL,
   ...
}

-- TAG-SIB6-STOP
-- TAG-SIB7-START
SIB7 ::= SEQUENCE {
   messageIdentifier [0] BIT STRING  (SIZE (16)),
   serialNumber [1] BIT STRING  (SIZE (16)),
   warningMessageSegmentType [2] ENUMERATED { notLastSegment(0), lastSegment(1)
       },
   warningMessageSegmentNumber [3] INTEGER (0..63),
   warningMessageSegment [4] OCTET STRING,
   dataCodingScheme [5] OCTET STRING (SIZE (1)) OPTIONAL, -- Cond Segment1
   lateNonCriticalExtension [6] OCTET STRING OPTIONAL,
   ...
}

-- TAG-SIB7-STOP
-- TAG-SIB8-START
SIB8 ::= SEQUENCE {
   messageIdentifier [0] BIT STRING  (SIZE (16)),
   serialNumber [1] BIT STRING  (SIZE (16)),
   warningMessageSegmentType [2] ENUMERATED { notLastSegment(0), lastSegment(1)
       },
   warningMessageSegmentNumber [3] INTEGER (0..63),
   warningMessageSegment [4] OCTET STRING,
   dataCodingScheme [5] OCTET STRING (SIZE (1)) OPTIONAL, -- Cond Segment1
   warningAreaCoordinatesSegment [6] OCTET STRING OPTIONAL, -- Need R
   lateNonCriticalExtension [7] OCTET STRING OPTIONAL,
   ...
}

ReferenceTime-r16 ::= SEQUENCE {
   refDays-r16 [0] INTEGER (0..72999),
   refSeconds-r16 [1] INTEGER (0..86399),
   refMilliSeconds-r16 [2] INTEGER (0..999),
   refTenNanoSeconds-r16 [3] INTEGER (0..99999)
}

-- TAG-REFERENCELOCATION-STOP
-- TAG-REFERENCETIMEINFO-START
ReferenceTimeInfo-r16 ::= SEQUENCE {
   time-r16 [0] ReferenceTime-r16,
   uncertainty-r16 [1] INTEGER (0..32767) OPTIONAL, -- Need S
   timeInfoType-r16 [2] ENUMERATED { localClock(0) } OPTIONAL, -- Need S
   referenceSFN-r16 [3] INTEGER (0..1023) OPTIONAL -- Cond RefTime
}

-- TAG-SIB8-STOP
-- TAG-SIB9-START
SIB9 ::= SEQUENCE {
   timeInfo [0] SEQUENCE {
      timeInfoUTC [0] INTEGER (0..549755813887),
      dayLightSavingTime [1] BIT STRING  (SIZE (2)) OPTIONAL, -- Need R
      leapSeconds [2] INTEGER (-127..128) OPTIONAL, -- Need R
      localTimeOffset [3] INTEGER (-63..64) OPTIONAL -- Need R
   } OPTIONAL, -- Need R
   lateNonCriticalExtension [1] OCTET STRING OPTIONAL,
   ...,
   [[
      referenceTimeInfo-r16 [2] ReferenceTimeInfo-r16 OPTIONAL
   ]]
}

HRNN-r16 ::= SEQUENCE {
   hrnn-r16 [0] OCTET STRING (SIZE (1..maxHRNN-Len-r16)) OPTIONAL -- Need R
}

HRNN-List-r16 ::= SEQUENCE (SIZE (1..maxNPN-r16)) OF HRNN-r16

-- TAG-SIB9-STOP
-- TAG-SIB10-START
SIB10-r16 ::= SEQUENCE {
   hrnn-List-r16 [0] HRNN-List-r16 OPTIONAL, -- Need R
   lateNonCriticalExtension [1] OCTET STRING OPTIONAL,
   ...
}

-- TAG-MSGA-PUSCH-CONFIG-STOP
-- TAG-MULTIFREQUENCYBANDLISTNR-START
MultiFrequencyBandListNR ::= SEQUENCE (SIZE (1..maxNrofMultiBands)) OF FreqBandIndicatorNR

CellListNR-r16 ::= SEQUENCE (SIZE (1..maxCellMeasIdle-r16)) OF PCI-Range

BeamMeasConfigIdle-NR-r16 ::= SEQUENCE {
   reportQuantityRS-Indexes-r16 [0] ENUMERATED { rsrp(0), rsrq(1), both(2) },
   maxNrofRS-IndexesToReport-r16 [1] INTEGER (1..maxNrofIndexesToReport),
   includeBeamMeasurements-r16 [2] BOOLEAN
}

MeasIdleCarrierNR-r16 ::= SEQUENCE {
   carrierFreq-r16 [0] ARFCN-ValueNR,
   ssbSubcarrierSpacing-r16 [1] SubcarrierSpacing,
   frequencyBandList [2] MultiFrequencyBandListNR OPTIONAL, -- Need R
   measCellListNR-r16 [3] CellListNR-r16 OPTIONAL, -- Need R
   reportQuantities-r16 [4] ENUMERATED { rsrp(0), rsrq(1), both(2) },
   qualityThreshold-r16 [5] SEQUENCE {
      idleRSRP-Threshold-NR-r16 [0] RSRP-Range OPTIONAL, -- Need R
      idleRSRQ-Threshold-NR-r16 [1] RSRQ-Range OPTIONAL -- Need R
   } OPTIONAL, -- Need R
   ssb-MeasConfig-r16 [6] SEQUENCE {
      nrofSS-BlocksToAverage-r16 [0] INTEGER (2..maxNrofSS-BlocksToAverage) OPTIONAL, -- Need S
      absThreshSS-BlocksConsolidation-r16 [1] ThresholdNR OPTIONAL, -- Need S
      smtc-r16 [2] SSB-MTC OPTIONAL, -- Need S
      ssb-ToMeasure-r16 [3] EXPLICIT SSB-ToMeasure OPTIONAL, -- Need S
      deriveSSB-IndexFromCell-r16 [4] BOOLEAN,
      ss-RSSI-Measurement-r16 [5] SS-RSSI-Measurement OPTIONAL -- Need S
   } OPTIONAL, -- Need S
   beamMeasConfigIdle-r16 [7] BeamMeasConfigIdle-NR-r16 OPTIONAL,
   ...
}

CellListEUTRA-r16 ::= SEQUENCE (SIZE (1..maxCellMeasIdle-r16)) OF EUTRA-PhysCellIdRange

RSRP-RangeEUTRA ::= INTEGER (0..97)

RSRQ-RangeEUTRA-r16 ::= INTEGER (-30..46)

MeasIdleCarrierEUTRA-r16 ::= SEQUENCE {
   carrierFreqEUTRA-r16 [0] ARFCN-ValueEUTRA,
   allowedMeasBandwidth-r16 [1] EUTRA-AllowedMeasBandwidth,
   measCellListEUTRA-r16 [2] CellListEUTRA-r16 OPTIONAL, -- Need R
   reportQuantitiesEUTRA-r16 [3] ENUMERATED { rsrp(0), rsrq(1), both(2) },
   qualityThresholdEUTRA-r16 [4] SEQUENCE {
      idleRSRP-Threshold-EUTRA-r16 [0] RSRP-RangeEUTRA OPTIONAL, -- Need R
      idleRSRQ-Threshold-EUTRA-r16 [1] RSRQ-RangeEUTRA-r16 OPTIONAL -- Need R
   } OPTIONAL,
   ...
}

-- TAG-MEASID-STOP
-- TAG-MEASIDLECONFIG-START
MeasIdleConfigSIB-r16 ::= SEQUENCE {
   measIdleCarrierListNR-r16 [0] SEQUENCE (SIZE (1..maxFreqIdle-r16)) OF MeasIdleCarrierNR-r16
       OPTIONAL, -- Need S
   measIdleCarrierListEUTRA-r16 [1] SEQUENCE (SIZE (1..maxFreqIdle-r16)) OF 
      MeasIdleCarrierEUTRA-r16 OPTIONAL,
   ...
}

-- TAG-SIB10-STOP
-- TAG-SIB11-START
SIB11-r16 ::= SEQUENCE {
   measIdleConfigSIB-r16 [0] MeasIdleConfigSIB-r16 OPTIONAL, -- Need S
   lateNonCriticalExtension [1] OCTET STRING OPTIONAL,
   ...
}

-- TAG-SIB11-STOP
-- TAG-SIB12-START
SIB12-r16 ::= SEQUENCE {
   segmentNumber-r16 [0] INTEGER (0..63),
   segmentType-r16 [1] ENUMERATED { notLastSegment(0), lastSegment(1) },
   segmentContainer-r16 [2] OCTET STRING
}

-- TAG-SIB12-STOP
-- TAG-SIB13-START
SIB13-r16 ::= SEQUENCE {
   sl-V2X-ConfigCommon-r16 [0] OCTET STRING,
   dummy [1] OCTET STRING,
   tdd-Config-r16 [2] OCTET STRING,
   lateNonCriticalExtension [3] OCTET STRING OPTIONAL,
   ...
}

-- TAG-SIB13-STOP
-- TAG-SIB14-START
SIB14-r16 ::= SEQUENCE {
   sl-V2X-ConfigCommonExt-r16 [0] OCTET STRING,
   lateNonCriticalExtension [1] OCTET STRING OPTIONAL,
   ...
}

ApplicableDisasterInfo-r17 ::= CHOICE {
   noDisasterRoaming-r17 [0] NULL,
   disasterRelatedIndication-r17 [1] NULL,
   commonPLMNs-r17 [2] NULL,
   dedicatedPLMNs-r17 [3] SEQUENCE (SIZE (1..maxPLMN)) OF PLMN-Identity
}

-- TAG-SIB14-STOP
-- TAG-SIB15-START
SIB15-r17 ::= SEQUENCE {
   commonPLMNsWithDisasterCondition-r17 [0] SEQUENCE (SIZE (1..maxPLMN)) OF 
      PLMN-Identity OPTIONAL, -- Need R
   applicableDisasterInfoList-r17 [1] SEQUENCE (SIZE (1..maxPLMN)) OF 
      ApplicableDisasterInfo-r17 OPTIONAL, -- Need R
   lateNonCriticalExtension [2] OCTET STRING OPTIONAL,
   ...
}

-- TAG-NR-NS-PMAXLIST-STOP
-- TAG-NSAG-ID-START
NSAG-ID-r17 ::= BIT STRING  (SIZE (8))

-- TAG-NSAG-ID-STOP
-- TAG-NSAG-IDENTITYINFO-START
NSAG-IdentityInfo-r17 ::= SEQUENCE {
   nsag-ID-r17 [0] NSAG-ID-r17,
   trackingAreaCode-r17 [1] TrackingAreaCode OPTIONAL -- Need R
}

SliceCellListNR-r17 ::= SEQUENCE (SIZE (1..maxCellSlice-r17)) OF PCI-Range

SliceInfo-r17 ::= SEQUENCE {
   nsag-IdentityInfo-r17 [0] NSAG-IdentityInfo-r17,
   nsag-CellReselectionPriority-r17 [1] CellReselectionPriority OPTIONAL, -- Need R
   nsag-CellReselectionSubPriority-r17 [2] CellReselectionSubPriority OPTIONAL,
       -- Need R
   sliceCellListNR-r17 [3] EXPLICIT CHOICE {
      sliceAllowedCellListNR-r17 [0] SliceCellListNR-r17,
      sliceExcludedCellListNR-r17 [1] SliceCellListNR-r17
   } OPTIONAL -- Need R
}

SliceInfoList-r17 ::= SEQUENCE (SIZE (1..maxSliceInfo-r17)) OF SliceInfo-r17

FreqPrioritySlicing-r17 ::= SEQUENCE {
   dl-ImplicitCarrierFreq-r17 [0] INTEGER (0..maxFreq),
   sliceInfoList-r17 [1] SliceInfoList-r17 OPTIONAL -- Cond Mandatory
}

-- TAG-FREQPRIORITYLISTDEDICATEDSLICING-STOP
-- TAG-FREQPRIORITYLISTSLICING-START
FreqPriorityListSlicing-r17 ::= SEQUENCE (SIZE (1..maxFreqPlus1)) OF FreqPrioritySlicing-r17
   

-- TAG-SIB15-STOP
-- TAG-SIB16-START
SIB16-r17 ::= SEQUENCE {
   freqPriorityListSlicing-r17 [0] FreqPriorityListSlicing-r17 OPTIONAL, -- Need R
   lateNonCriticalExtension [1] OCTET STRING OPTIONAL,
   ...
}

-- TAG-SIB16-STOP
-- TAG-SIB17-START
SIB17-r17 ::= SEQUENCE {
   segmentNumber-r17 [0] INTEGER (0..63),
   segmentType-r17 [1] ENUMERATED { notLastSegment(0), lastSegment(1) },
   segmentContainer-r17 [2] OCTET STRING
}

NID-r16 ::= BIT STRING  (SIZE (44))

GIN-Element-r17 ::= SEQUENCE {
   plmn-Identity-r17 [0] PLMN-Identity,
   nid-List-r17 [1] SEQUENCE (SIZE (1..maxGIN-r17)) OF NID-r16
}

GINs-PerSNPN-r17 ::= SEQUENCE {
   supportedGINs-r17 [0] BIT STRING  (SIZE (1..maxGIN-r17)) OPTIONAL -- Need R
}

-- TAG-SIB17-STOP
-- TAG-SIB18-START
SIB18-r17 ::= SEQUENCE {
   gin-ElementList-r17 [0] SEQUENCE (SIZE (1..maxGIN-r17)) OF GIN-Element-r17 OPTIONAL, -- Need R
   gins-PerSNPN-List-r17 [1] SEQUENCE (SIZE (1..maxNPN-r16)) OF GINs-PerSNPN-r17 OPTIONAL,
       -- Need S
   lateNonCriticalExtension [2] OCTET STRING OPTIONAL,
   ...
}

EpochTime-r17 ::= SEQUENCE {
   sfn-r17 [0] INTEGER (0..1023),
   subFrameNR-r17 [1] INTEGER (0..9)
}

TA-Info-r17 ::= SEQUENCE {
   ta-Common-r17 [0] INTEGER (0..66485757),
   ta-CommonDrift-r17 [1] INTEGER (-257303..257303) OPTIONAL, -- Need R
   ta-CommonDriftVariant-r17 [2] INTEGER (0..28949) OPTIONAL -- Need R
}

PositionStateVector-r17 ::= INTEGER (-33554432..33554431)

VelocityStateVector-r17 ::= INTEGER (-131072..131071)

PositionVelocity-r17 ::= SEQUENCE {
   positionX-r17 [0] PositionStateVector-r17,
   positionY-r17 [1] PositionStateVector-r17,
   positionZ-r17 [2] PositionStateVector-r17,
   velocityVX-r17 [3] VelocityStateVector-r17,
   velocityVY-r17 [4] VelocityStateVector-r17,
   velocityVZ-r17 [5] VelocityStateVector-r17
}

Orbital-r17 ::= SEQUENCE {
   semiMajorAxis-r17 [0] INTEGER (0..8589934591),
   eccentricity-r17 [1] INTEGER (0..1048575),
   periapsis-r17 [2] INTEGER (0..268435455),
   longitude-r17 [3] INTEGER (0..268435455),
   inclination-r17 [4] INTEGER (-67108864..67108863),
   meanAnomaly-r17 [5] INTEGER (0..268435455)
}

-- TAG-DRX-CONFIGSL-STOP
-- TAG-EPHEMERISINFO-START
EphemerisInfo-r17 ::= CHOICE {
   positionVelocity-r17 [0] PositionVelocity-r17,
   orbital-r17 [1] Orbital-r17
}

-- TAG-NSAG-IDENTITYINFO-STOP
-- TAG-NTN-CONFIG-START
NTN-Config-r17 ::= SEQUENCE {
   epochTime-r17 [0] EpochTime-r17 OPTIONAL, -- Need R
   ntn-UlSyncValidityDuration-r17 [1] ENUMERATED { s5(0), s10(1), s15(2), 
      s20(3), s25(4), s30(5), s35(6), s40(7), s45(8), s50(9), s55(10), s60(11)
      , s120(12), s180(13), s240(14), s900(15) } OPTIONAL, -- Cond SIB19
   cellSpecificKoffset-r17 [2] INTEGER (1..1023) OPTIONAL, -- Need R
   kmac-r17 [3] INTEGER (1..512) OPTIONAL, -- Need R
   ta-Info-r17 [4] TA-Info-r17 OPTIONAL, -- Need R
   ntn-PolarizationDL-r17 [5] ENUMERATED { rhcp(0), lhcp(1), linear(2) }
       OPTIONAL, -- Need R
   ntn-PolarizationUL-r17 [6] ENUMERATED { rhcp(0), lhcp(1), linear(2) }
       OPTIONAL, -- Need R
   ephemerisInfo-r17 [7] EXPLICIT EphemerisInfo-r17 OPTIONAL, -- Need R
   ta-Report-r17 [8] ENUMERATED { enabled(0) } OPTIONAL,
   ...
}

-- TAG-RATEMATCHPATTERNLTE-CRS-STOP
-- TAG-REFERENCELOCATION-START
ReferenceLocation-r17 ::= OCTET STRING

NTN-NeighCellConfig-r17 ::= SEQUENCE {
   ntn-Config-r17 [0] NTN-Config-r17 OPTIONAL, -- Need R
   carrierFreq-r17 [1] ARFCN-ValueNR OPTIONAL, -- Need R
   physCellId-r17 [2] PhysCellId OPTIONAL -- Need R
}

NTN-NeighCellConfigList-r17 ::= SEQUENCE (SIZE (1..maxCellNTN-r17)) OF NTN-NeighCellConfig-r17
   

-- TAG-SIB18-STOP
-- TAG-SIB19-START
SIB19-r17 ::= SEQUENCE {
   ntn-Config-r17 [0] NTN-Config-r17 OPTIONAL, -- Need R
   t-Service-r17 [1] INTEGER (0..549755813887) OPTIONAL, -- Need R
   referenceLocation-r17 [2] ReferenceLocation-r17 OPTIONAL, -- Need R
   distanceThresh-r17 [3] INTEGER (0..65525) OPTIONAL, -- Need R
   ntn-NeighCellConfigList-r17 [4] NTN-NeighCellConfigList-r17 OPTIONAL, -- Need R
   lateNonCriticalExtension [5] OCTET STRING OPTIONAL,
   ...,
   [[
      ntn-NeighCellConfigListExt-v1720 [6] NTN-NeighCellConfigList-r17 OPTIONAL
   ]]
}

MCCH-RepetitionPeriodAndOffset-r17 ::= CHOICE {
   rf1-r17 [0] INTEGER (0),
   rf2-r17 [1] INTEGER (0..1),
   rf4-r17 [2] INTEGER (0..3),
   rf8-r17 [3] INTEGER (0..7),
   rf16-r17 [4] INTEGER (0..15),
   rf32-r17 [5] INTEGER (0..31),
   rf64-r17 [6] INTEGER (0..63),
   rf128-r17 [7] INTEGER (0..127),
   rf256-r17 [8] INTEGER (0..255)
}

MCCH-Config-r17 ::= SEQUENCE {
   mcch-RepetitionPeriodAndOffset-r17 [0] EXPLICIT 
      MCCH-RepetitionPeriodAndOffset-r17,
   mcch-WindowStartSlot-r17 [1] INTEGER (0..79),
   mcch-WindowDuration-r17 [2] ENUMERATED { sl2(0), sl4(1), sl8(2), sl10(3), 
      sl20(4), sl40(5), sl80(6), sl160(7) } OPTIONAL, -- Need S
   mcch-ModificationPeriod-r17 [3] ENUMERATED { rf2(0), rf4(1), rf8(2), rf16(3)
      , rf32(4), rf64(5), rf128(6), rf256(7), rf512(8), rf1024(9), rf2048(10), 
      rf4096(11), rf8192(12), rf16384(13), rf32768(14), rf65536(15) }
}

LocationAndBandwidthBroadcast-r17 ::= CHOICE {
   sameAsSib1ConfiguredLocationAndBW [0] NULL,
   locationAndBandwidth [1] INTEGER (0..37949)
}

PDSCH-ConfigPTM-r17 ::= SEQUENCE {
   dataScramblingIdentityPDSCH-r17 [0] INTEGER (0..1023) OPTIONAL, -- Need S
   dmrs-ScramblingID0-r17 [1] INTEGER (0..65535) OPTIONAL, -- Need S
   pdsch-AggregationFactor-r17 [2] ENUMERATED { n2(0), n4(1), n8(2) } OPTIONAL -- Need S
}

EUTRA-MBSFN-SubframeConfig ::= SEQUENCE {
   radioframeAllocationPeriod [0] ENUMERATED { n1(0), n2(1), n4(2), n8(3), 
      n16(4), n32(5) },
   radioframeAllocationOffset [1] INTEGER (0..7),
   subframeAllocation1 [2] EXPLICIT CHOICE {
      oneFrame [0] BIT STRING  (SIZE (6)),
      fourFrames [1] BIT STRING  (SIZE (24))
   },
   subframeAllocation2 [3] EXPLICIT CHOICE {
      oneFrame [0] BIT STRING  (SIZE (2)),
      fourFrames [1] BIT STRING  (SIZE (8))
   } OPTIONAL,
   ...
}

-- TAG-EUTRA-ALLOWEDMEASBANDWIDTH-STOP
-- TAG-EUTRA-MBSFN-SUBFRAMECONFIGLIST-START
EUTRA-MBSFN-SubframeConfigList ::= SEQUENCE (SIZE (1..maxMBSFN-Allocations)) OF 
   EUTRA-MBSFN-SubframeConfig

-- TAG-RATEMATCHPATTERNID-STOP
-- TAG-RATEMATCHPATTERNLTE-CRS-START
RateMatchPatternLTE-CRS ::= SEQUENCE {
   carrierFreqDL [0] INTEGER (0..16383),
   carrierBandwidthDL [1] ENUMERATED { n6(0), n15(1), n25(2), n50(3), n75(4), 
      n100(5), spare2(6), spare1(7) },
   mbsfn-SubframeConfigList [2] EUTRA-MBSFN-SubframeConfigList OPTIONAL, -- Need M
   nrofCRS-Ports [3] ENUMERATED { n1(0), n2(1), n4(2) },
   v-Shift [4] ENUMERATED { n0(0), n1(1), n2(2), n3(3), n4(4), n5(5) }
}

-- TAG-MTCH-SSB-MAPPINGWINDOWLIST-STOP
-- TAG-PDSCH-CONFIGBROADCAST-START
PDSCH-ConfigBroadcast-r17 ::= SEQUENCE {
   pdschConfigList-r17 [0] SEQUENCE (SIZE (1..maxNrofPDSCH-ConfigPTM-r17)) OF PDSCH-ConfigPTM-r17,
   pdsch-TimeDomainAllocationList-r17 [1] 
      PDSCH-TimeDomainResourceAllocationList-r16 OPTIONAL, -- Need R
   rateMatchPatternToAddModList-r17 [2] SEQUENCE (SIZE (1..maxNrofRateMatchPatterns)) OF 
      RateMatchPattern OPTIONAL, -- Need R
   lte-CRS-ToMatchAround-r17 [3] RateMatchPatternLTE-CRS OPTIONAL, -- Need R
   mcs-Table-r17 [4] ENUMERATED { qam256(0), qam64LowSE(1) } OPTIONAL, -- Need S
   xOverhead-r17 [5] ENUMERATED { xOh6(0), xOh12(1), xOh18(2) } OPTIONAL -- Need S
}

-- TAG-CARRIERFREQLISTMBS-STOP
-- TAG-CFR-CONFIGMCCH-MTCH-START
CFR-ConfigMCCH-MTCH-r17 ::= SEQUENCE {
   locationAndBandwidthBroadcast-r17 [0] EXPLICIT 
      LocationAndBandwidthBroadcast-r17 OPTIONAL, -- Need S
   pdsch-ConfigMCCH-r17 [1] PDSCH-ConfigBroadcast-r17 OPTIONAL, -- Need S
   commonControlResourceSetExt-r17 [2] ControlResourceSet OPTIONAL -- Cond NotSIB1CommonControlResource
}

-- TAG-SIB19-STOP
-- TAG-SIB20-START
SIB20-r17 ::= SEQUENCE {
   mcch-Config-r17 [0] MCCH-Config-r17,
   cfr-ConfigMCCH-MTCH-r17 [1] CFR-ConfigMCCH-MTCH-r17 OPTIONAL, -- Need S
   lateNonCriticalExtension [2] OCTET STRING OPTIONAL,
   ...
}

MBS-FSAI-List-r17 ::= SEQUENCE (SIZE (1..maxFSAI-MBS-r17)) OF MBS-FSAI-r17

MBS-FSAI-InterFreq-r17 ::= SEQUENCE {
   dl-CarrierFreq-r17 [0] ARFCN-ValueNR,
   mbs-FSAI-List-r17 [1] MBS-FSAI-List-r17
}

MBS-FSAI-InterFreqList-r17 ::= SEQUENCE (SIZE (1..maxFreq)) OF MBS-FSAI-InterFreq-r17

-- TAG-SIB20-STOP
-- TAG-SIB21-START
SIB21-r17 ::= SEQUENCE {
   mbs-FSAI-IntraFreq-r17 [0] MBS-FSAI-List-r17 OPTIONAL, -- Need R
   mbs-FSAI-InterFreqList-r17 [1] MBS-FSAI-InterFreqList-r17 OPTIONAL, -- Need R
   lateNonCriticalExtension [2] OCTET STRING OPTIONAL,
   ...
}

SystemInformation-IEs ::= SEQUENCE {
   sib-TypeAndInfo [0] SEQUENCE (SIZE (1..maxSIB)) OF CHOICE {
      sib2 [0] SIB2,
      sib3 [1] SIB3,
      sib4 [2] SIB4,
      sib5 [3] SIB5,
      sib6 [4] SIB6,
      sib7 [5] SIB7,
      sib8 [6] SIB8,
      sib9 [7] SIB9,
      ...,
      sib10-v1610 [8] SIB10-r16,
      sib11-v1610 [9] SIB11-r16,
      sib12-v1610 [10] SIB12-r16,
      sib13-v1610 [11] SIB13-r16,
      sib14-v1610 [12] SIB14-r16,
      sib15-v1700 [13] SIB15-r17,
      sib16-v1700 [14] SIB16-r17,
      sib17-v1700 [15] SIB17-r17,
      sib18-v1700 [16] SIB18-r17,
      sib19-v1700 [17] SIB19-r17,
      sib20-v1700 [18] SIB20-r17,
      sib21-v1700 [19] SIB21-r17
   },
   lateNonCriticalExtension [1] OCTET STRING OPTIONAL,
   nonCriticalExtension [2] SEQUENCE {

   } OPTIONAL
}

-- TAG-POSSI-SCHEDULINGINFO-STOP
-- TAG-SIPOS-START
SIBpos-r16 ::= SEQUENCE {
   assistanceDataSIB-Element-r16 [0] OCTET STRING,
   lateNonCriticalExtension [1] OCTET STRING OPTIONAL,
   ...
}

-- TAG-SIB21-STOP
-- TAG-POSSYSTEMINFORMATION-R16-IES-START
PosSystemInformation-r16-IEs ::= SEQUENCE {
   posSIB-TypeAndInfo-r16 [0] SEQUENCE (SIZE (1..maxSIB)) OF CHOICE {
      posSib1-1-r16 [0] SIBpos-r16,
      posSib1-2-r16 [1] SIBpos-r16,
      posSib1-3-r16 [2] SIBpos-r16,
      posSib1-4-r16 [3] SIBpos-r16,
      posSib1-5-r16 [4] SIBpos-r16,
      posSib1-6-r16 [5] SIBpos-r16,
      posSib1-7-r16 [6] SIBpos-r16,
      posSib1-8-r16 [7] SIBpos-r16,
      posSib2-1-r16 [8] SIBpos-r16,
      posSib2-2-r16 [9] SIBpos-r16,
      posSib2-3-r16 [10] SIBpos-r16,
      posSib2-4-r16 [11] SIBpos-r16,
      posSib2-5-r16 [12] SIBpos-r16,
      posSib2-6-r16 [13] SIBpos-r16,
      posSib2-7-r16 [14] SIBpos-r16,
      posSib2-8-r16 [15] SIBpos-r16,
      posSib2-9-r16 [16] SIBpos-r16,
      posSib2-10-r16 [17] SIBpos-r16,
      posSib2-11-r16 [18] SIBpos-r16,
      posSib2-12-r16 [19] SIBpos-r16,
      posSib2-13-r16 [20] SIBpos-r16,
      posSib2-14-r16 [21] SIBpos-r16,
      posSib2-15-r16 [22] SIBpos-r16,
      posSib2-16-r16 [23] SIBpos-r16,
      posSib2-17-r16 [24] SIBpos-r16,
      posSib2-18-r16 [25] SIBpos-r16,
      posSib2-19-r16 [26] SIBpos-r16,
      posSib2-20-r16 [27] SIBpos-r16,
      posSib2-21-r16 [28] SIBpos-r16,
      posSib2-22-r16 [29] SIBpos-r16,
      posSib2-23-r16 [30] SIBpos-r16,
      posSib3-1-r16 [31] SIBpos-r16,
      posSib4-1-r16 [32] SIBpos-r16,
      posSib5-1-r16 [33] SIBpos-r16,
      posSib6-1-r16 [34] SIBpos-r16,
      posSib6-2-r16 [35] SIBpos-r16,
      posSib6-3-r16 [36] SIBpos-r16,
      ...,
      posSib1-9-v1700 [37] SIBpos-r16,
      posSib1-10-v1700 [38] SIBpos-r16,
      posSib2-24-v1700 [39] SIBpos-r16,
      posSib2-25-v1700 [40] SIBpos-r16,
      posSib6-4-v1700 [41] SIBpos-r16,
      posSib6-5-v1700 [42] SIBpos-r16,
      posSib6-6-v1700 [43] SIBpos-r16,
      posSib2-17a-v1770 [44] SIBpos-r16,
      posSib2-18a-v1770 [45] SIBpos-r16,
      posSib2-20a-v1770 [46] SIBpos-r16
   },
   lateNonCriticalExtension [1] OCTET STRING OPTIONAL,
   nonCriticalExtension [2] SEQUENCE {

   } OPTIONAL
}

-- TAG-SIDELINKUEINFORMATIONNR-STOP
-- TAG-SYSTEMINFORMATION-START
SystemInformation ::= SEQUENCE {
   criticalExtensions [0] EXPLICIT CHOICE {
      systemInformation [0] SystemInformation-IEs,
      criticalExtensionsFuture-r16 [1] EXPLICIT CHOICE {
         posSystemInformation-r16 [0] PosSystemInformation-r16-IEs,
         criticalExtensionsFuture [1] SEQUENCE {

         }
      }
   }
}

SCellSIB20-r17 ::= OCTET STRING (CONTAINING SystemInformation)

IAB-ResourceConfigID-r17 ::= INTEGER (0..maxNrofIABResourceConfig-1-r17)

-- TAG-CELLGROUPCONFIG-STOP
-- TAG-CELLGROUPID-START
CellGroupId ::= INTEGER (0..maxSecondaryCellGroups)

-- TAG-CGI-INFO-LOGGING-STOP
-- TAG-CLI-RSSI-RANGE-START
CLI-RSSI-Range-r16 ::= INTEGER (0..76)

-- TAG-COMMONLOCATIONINFO-STOP
-- TAG-CONDRECONFIGID-START
CondReconfigId-r16 ::= INTEGER (1..maxNrofCondCells-r16)

-- TAG-CONTROLRESOURCESETID-STOP
-- TAG-CONTROLRESOURCESETZERO-START
ControlResourceSetZero ::= INTEGER (0..15)

-- TAG-CSI-IM-RESOURCE-STOP
-- TAG-CSI-IM-RESOURCEID-START
CSI-IM-ResourceId ::= INTEGER (0..maxNrofCSI-IM-Resources-1)

-- TAG-CSI-IM-RESOURCESET-STOP
-- TAG-CSI-IM-RESOURCESETID-START
CSI-IM-ResourceSetId ::= INTEGER (0..maxNrofCSI-IM-ResourceSets-1)

PortIndex8 ::= INTEGER (0..7)

PortIndex4 ::= INTEGER (0..3)

PortIndex2 ::= INTEGER (0..1)

-- TAG-CSI-REPORTCONFIG-STOP
-- TAG-CSI-REPORTCONFIGID-START
CSI-ReportConfigId ::= INTEGER (0..maxNrofCSI-ReportConfigurations-1)

-- TAG-CSI-RESOURCECONFIG-STOP
-- TAG-CSI-RESOURCECONFIGID-START
CSI-ResourceConfigId ::= INTEGER (0..maxNrofCSI-ResourceConfigurations-1)

CSI-RS-Index ::= INTEGER (0..maxNrofCSI-RS-ResourcesRRM-1)

ServingAdditionalPCIIndex-r17 ::= INTEGER (0..maxNrofAdditionalPCI-r17)

-- TAG-CSI-SSB-RESOURCESET-STOP
-- TAG-CSI-SSB-RESOURCESETID-START
CSI-SSB-ResourceSetId ::= INTEGER (0..maxNrofCSI-SSB-ResourceSets-1)

-- TAG-CSI-SSB-RESOURCESETID-STOP
-- TAG-DEDICATED-NAS-MESSAGE-START
DedicatedNAS-Message ::= OCTET STRING

DL-PPW-ID-r17 ::= INTEGER (0..maxNrofPPW-ID-1-r17)

-- TAG-DOWNLINKPREEMPTION-STOP
-- TAG-DRB-IDENTITY-START
DRB-Identity ::= INTEGER (1..32)

-- TAG-FEATURECOMBINATIONPREAMBLES-STOP
-- TAG-FILTERCOEFFICIENT-START
FilterCoefficient ::= ENUMERATED { fc0(0), fc1(1), fc2(2), fc3(3), fc4(4), 
   fc5(5), fc6(6), fc7(7), fc8(8), fc9(9), fc11(10), fc13(11), fc15(12), 
   fc17(13), fc19(14), spare1(15), ... }

-- TAG-FREQUENCYINFOUL-SIB-STOP
-- TAG-GAPPRIORITY-START
GapPriority-r17 ::= INTEGER (1..maxNrOfGapPri-r17)

-- TAG-HIGHSPEEDCONFIG-STOP
-- TAG-HYSTERESIS-START
Hysteresis ::= INTEGER (0..30)

-- TAG-HYSTERESIS-STOP
-- TAG-HYSTERESISLOCATION-START
HysteresisLocation-r17 ::= INTEGER (0..32768)

-- TAG-INVALIDSYMBOLPATTERN-STOP
-- TAG-I-RNTI-VALUE-START
I-RNTI-Value ::= BIT STRING  (SIZE (40))

DataInactivityTimer ::= ENUMERATED { s1(0), s2(1), s3(2), s5(3), s7(4), s10(5)
   , s15(6), s20(7), s40(8), s50(9), s60(10), s80(11), s100(12), s120(13), 
   s150(14), s180(15) }

MBS-RNTI-SpecificConfigId-r17 ::= INTEGER (0..maxG-RNTI-1-r17)

MeasPosPreConfigGapId-r17 ::= INTEGER (1..maxNrofPreConfigPosGapId-r17)

-- TAG-MEASGAPCONFIG-STOP
-- TAG-MEASGAPID-START
MeasGapId-r17 ::= INTEGER (1..maxNrofGapId-r17)

MeasGapSharingScheme ::= ENUMERATED { scheme00(0), scheme01(1), scheme10(2), 
   scheme11(3) }

-- TAG-MEASGAPSHARINGCONFIG-STOP
-- TAG-MEASID-START
MeasId ::= INTEGER (1..maxNrofMeasId)

RSSI-ResourceId-r16 ::= INTEGER (0..maxNrofCLI-RSSI-Resources-1-r16)

EUTRA-CellIndex ::= INTEGER (1..maxCellMeasEUTRA)

-- TAG-MEASOBJECTEUTRA-STOP
-- TAG-MEASOBJECTID-START
MeasObjectId ::= INTEGER (1..maxNrofObjectId)

T312-r16 ::= ENUMERATED { ms0(0), ms50(1), ms100(2), ms200(3), ms300(4), 
   ms400(5), ms500(6), ms1000(7) }

UTRA-FDD-CellIndex-r16 ::= INTEGER (1..maxCellMeasUTRA-FDD-r16)

TimeBetweenEvent-r17 ::= INTEGER (0..1023)

RSRQ-RangeEUTRA ::= INTEGER (0..34)

SINR-RangeEUTRA ::= INTEGER (0..127)

-- TAG-MOBILITYSTATEPARAMETERS-STOP
-- TAG-MRB-IDENTITY-START
MRB-Identity-r17 ::= INTEGER (1..512)

-- TAG-MUSIM-GAPCONFIG-STOP
-- TAG-MUSIM-GAPID-START
MUSIM-GapId-r17 ::= INTEGER (0..2)

-- TAG-NEEDFORGAPNCSG-INFONR-STOP
-- TAG-NEXTHOPCHAININGCOUNT-START
NextHopChainingCount ::= INTEGER (0..7)

-- TAG-NEXTHOPCHAININGCOUNT-STOP
-- TAG-NG-5G-S-TMSI-START
NG-5G-S-TMSI ::= BIT STRING  (SIZE (48))

NR-DL-PRS-ResourceID-r17 ::= INTEGER (0..maxNrofPRS-ResourcesPerSet-1-r17)

-- TAG-NZP-CSI-RS-RESOURCESET-STOP
-- TAG-NZP-CSI-RS-RESOURCESETID-START
NZP-CSI-RS-ResourceSetId ::= INTEGER (0..maxNrofNZP-CSI-RS-ResourceSets-1)

-- TAG-PCI-RANGEELEMENT-STOP
-- TAG-PCI-RANGEINDEX-START
PCI-RangeIndex ::= INTEGER (1..maxNrofPCI-Ranges)

UL-DataSplitThreshold ::= ENUMERATED { b0(0), b100(1), b200(2), b400(3), 
   b800(4), b1600(5), b3200(6), b6400(7), b12800(8), b25600(9), b51200(10), 
   b102400(11), b204800(12), b409600(13), b819200(14), b1228800(15), 
   b1638400(16), b2457600(17), b3276800(18), b4096000(19), b4915200(20), 
   b5734400(21), b6553600(22), infinity(23), spare8(24), spare7(25), spare6(26)
   , spare5(27), spare4(28), spare3(29), spare2(30), spare1(31) }

DiscardTimerExt-r16 ::= ENUMERATED { ms0dot5(0), ms1(1), ms2(2), ms4(3), ms6(4)
   , ms8(5), spare2(6), spare1(7) }

DiscardTimerExt2-r17 ::= ENUMERATED { ms2000(0), spare3(1), spare2(2), 
   spare1(3) }

DownlinkHARQ-FeedbackDisabled-r17 ::= BIT STRING  (SIZE (32))

PDSCH-HARQ-ACK-EnhType3Index-r17 ::= INTEGER (0..maxNrofEnhType3HARQ-ACK-1-r17)

PDCCH-BlindDetection ::= INTEGER (1..15)

PDCCH-BlindDetection2-r16 ::= INTEGER (1..15)

PDCCH-BlindDetection3-r16 ::= INTEGER (1..15)

PDCCH-BlindDetection4-r17 ::= INTEGER (1..15)

-- TAG-PLMNIDENTITYLIST2-STOP
-- TAG-PRB-ID-START
PRB-Id ::= INTEGER (0..maxNrofPhysicalResourceBlocks-1)

PUCCH-MaxCodeRate ::= ENUMERATED { zeroDot08(0), zeroDot15(1), zeroDot25(2), 
   zeroDot35(3), zeroDot45(4), zeroDot60(5), zeroDot80(6) }

PUCCH-ResourceSetId ::= INTEGER (0..maxNrofPUCCH-ResourceSets-1)

PUCCH-ResourceId ::= INTEGER (0..maxNrofPUCCH-Resources-1)

PUCCH-ResourceGroupId-r16 ::= INTEGER (0..maxNrofPUCCH-ResourceGroups-1-r16)

-- TAG-PUCCH-CONFIGURATIONLIST-STOP
-- TAG-PUCCH-PATHLOSSREFERENCERS-ID-START
PUCCH-PathlossReferenceRS-Id ::= INTEGER (0..maxNrofPUCCH-PathlossReferenceRSs-1)

PUCCH-PathlossReferenceRS-Id-v1610 ::= INTEGER (maxNrofPUCCH-PathlossReferenceRSs..maxNrofPUCCH-PathlossReferenceRSs-1-r16)

PUCCH-PathlossReferenceRS-Id-r17 ::= INTEGER (0..maxNrofPUCCH-PathlossReferenceRSs-1-r17)

P0-PUCCH-Id ::= INTEGER (1..8)

PUCCH-PowerControlSetInfoId-r17 ::= INTEGER (1..maxNrofPowerControlSetInfos-r17)

-- TAG-PUCCH-SPATIALRELATIONINFO-STOP
-- TAG-PUCCH-SPATIALRELATIONINFO-START
PUCCH-SpatialRelationInfoId ::= INTEGER (1..maxNrofSpatialRelationInfos)

PUCCH-SpatialRelationInfoId-r16 ::= INTEGER (1..maxNrofSpatialRelationInfos-r16)

PUCCH-SpatialRelationInfoId-v1610 ::= INTEGER (maxNrofSpatialRelationInfos-plus-1..maxNrofSpatialRelationInfos-r16)

MaxMIMO-LayersDCI-0-2-r16 ::= INTEGER (1..4)

UplinkHARQ-mode-r17 ::= BIT STRING  (SIZE (32))

BeamLinkMonitoringRS-Id-r17 ::= INTEGER (0..maxNrofFailureDetectionResources-1-r17)

-- TAG-RADIOLINKMONITORINGCONFIG-STOP
-- TAG-RADIOLINKMONITORINGRS-ID-START
RadioLinkMonitoringRS-Id ::= INTEGER (0..maxNrofFailureDetectionResources-1)

-- TAG-REFERENCETIMEINFO-STOP
-- TAG-REJECTWAITTIME-START
RejectWaitTime ::= INTEGER (1..16)

-- TAG-REPETITIONSCHEMECONFIG-STOP
-- TAG-REPORTCONFIGID-START
ReportConfigId ::= INTEGER (1..maxReportConfigId)

NR-RS-Type ::= ENUMERATED { ssb(0), csi-rs(1) }

RxTxReportInterval-r17 ::= ENUMERATED { ms80(0), ms120(1), ms160(2), ms240(3), 
   ms320(4), ms480(5), ms640(6), ms1024(7), ms1280(8), ms2048(9), ms2560(10), 
   ms5120(11), spare4(12), spare3(13), spare2(14), spare1(15) }

MeasReportQuantityCLI-r16 ::= ENUMERATED { srs-rsrp(0), cli-rssi(1) }

-- TAG-REPORTCONFIGTOADDMODLIST-STOP
-- TAG-REPORTINTERVAL-START
ReportInterval ::= ENUMERATED { ms120(0), ms240(1), ms480(2), ms640(3), 
   ms1024(4), ms2048(5), ms5120(6), ms10240(7), ms20480(8), ms40960(9), 
   min1(10), min6(11), min12(12), min30(13) }

-- TAG-RESELECTIONTHRESHOLDQ-STOP
-- TAG-RESUMECAUSE-START
ResumeCause ::= ENUMERATED { emergency(0), highPriorityAccess(1), mt-Access(2)
   , mo-Signalling(3), mo-Data(4), mo-VoiceCall(5), mo-VideoCall(6), mo-SMS(7)
   , rna-Update(8), mps-PriorityAccess(9), mcs-PriorityAccess(10), spare1(11), 
   spare2(12), spare3(13), spare4(14), spare5(15) }

LogicalChannelIdentityExt-r17 ::= INTEGER (320..65855)

T-PollRetransmit ::= ENUMERATED { ms5(0), ms10(1), ms15(2), ms20(3), ms25(4), 
   ms30(5), ms35(6), ms40(7), ms45(8), ms50(9), ms55(10), ms60(11), ms65(12), 
   ms70(13), ms75(14), ms80(15), ms85(16), ms90(17), ms95(18), ms100(19), 
   ms105(20), ms110(21), ms115(22), ms120(23), ms125(24), ms130(25), ms135(26)
   , ms140(27), ms145(28), ms150(29), ms155(30), ms160(31), ms165(32), 
   ms170(33), ms175(34), ms180(35), ms185(36), ms190(37), ms195(38), ms200(39)
   , ms205(40), ms210(41), ms215(42), ms220(43), ms225(44), ms230(45), 
   ms235(46), ms240(47), ms245(48), ms250(49), ms300(50), ms350(51), ms400(52)
   , ms450(53), ms500(54), ms800(55), ms1000(56), ms2000(57), ms4000(58), 
   ms1-v1610(59), ms2-v1610(60), ms3-v1610(61), ms4-v1610(62), spare1(63) }

PollPDU ::= ENUMERATED { p4(0), p8(1), p16(2), p32(3), p64(4), p128(5), p256(6)
   , p512(7), p1024(8), p2048(9), p4096(10), p6144(11), p8192(12), p12288(13), 
   p16384(14), p20480(15), p24576(16), p28672(17), p32768(18), p40960(19), 
   p49152(20), p57344(21), p65536(22), infinity(23), spare8(24), spare7(25), 
   spare6(26), spare5(27), spare4(28), spare3(29), spare2(30), spare1(31) }

PollByte ::= ENUMERATED { kB1(0), kB2(1), kB5(2), kB8(3), kB10(4), kB15(5), 
   kB25(6), kB50(7), kB75(8), kB100(9), kB125(10), kB250(11), kB375(12), 
   kB500(13), kB750(14), kB1000(15), kB1250(16), kB1500(17), kB2000(18), 
   kB3000(19), kB4000(20), kB4500(21), kB5000(22), kB5500(23), kB6000(24), 
   kB6500(25), kB7000(26), kB7500(27), mB8(28), mB9(29), mB10(30), mB11(31), 
   mB12(32), mB13(33), mB14(34), mB15(35), mB16(36), mB17(37), mB18(38), 
   mB20(39), mB25(40), mB30(41), mB40(42), infinity(43), spare20(44), 
   spare19(45), spare18(46), spare17(47), spare16(48), spare15(49), spare14(50)
   , spare13(51), spare12(52), spare11(53), spare10(54), spare9(55), spare8(56)
   , spare7(57), spare6(58), spare5(59), spare4(60), spare3(61), spare2(62), 
   spare1(63) }

T-Reassembly ::= ENUMERATED { ms0(0), ms5(1), ms10(2), ms15(3), ms20(4), 
   ms25(5), ms30(6), ms35(7), ms40(8), ms45(9), ms50(10), ms55(11), ms60(12), 
   ms65(13), ms70(14), ms75(15), ms80(16), ms85(17), ms90(18), ms95(19), 
   ms100(20), ms110(21), ms120(22), ms130(23), ms140(24), ms150(25), ms160(26)
   , ms170(27), ms180(28), ms190(29), ms200(30), spare1(31) }

T-StatusProhibit ::= ENUMERATED { ms0(0), ms5(1), ms10(2), ms15(3), ms20(4), 
   ms25(5), ms30(6), ms35(7), ms40(8), ms45(9), ms50(10), ms55(11), ms60(12), 
   ms65(13), ms70(14), ms75(15), ms80(16), ms85(17), ms90(18), ms95(19), 
   ms100(20), ms105(21), ms110(22), ms115(23), ms120(24), ms125(25), ms130(26)
   , ms135(27), ms140(28), ms145(29), ms150(30), ms155(31), ms160(32), 
   ms165(33), ms170(34), ms175(35), ms180(36), ms185(37), ms190(38), ms195(39)
   , ms200(40), ms205(41), ms210(42), ms215(43), ms220(44), ms225(45), 
   ms230(46), ms235(47), ms240(48), ms245(49), ms250(50), ms300(51), ms350(52)
   , ms400(53), ms450(54), ms500(55), ms800(56), ms1000(57), ms1200(58), 
   ms1600(59), ms2000(60), ms2400(61), spare2(62), spare1(63) }

SN-FieldLengthUM ::= ENUMERATED { size6(0), size12(1) }

SN-FieldLengthAM ::= ENUMERATED { size12(0), size18(1) }

T-StatusProhibit-v1610 ::= ENUMERATED { ms1(0), ms2(1), ms3(2), ms4(3), 
   spare4(4), spare3(5), spare2(6), spare1(7) }

T-ReassemblyExt-r17 ::= ENUMERATED { ms210(0), ms220(1), ms340(2), ms350(3), 
   ms550(4), ms1100(5), ms1650(6), ms2200(7) }

-- TAG-RSRQ-RANGE-STOP
-- TAG-RSSI-RANGE-START
RSSI-Range-r16 ::= INTEGER (0..76)

-- TAG-SCELLACTIVATIONRS-CONFIG-STOP
-- TAG-SCELLACTIVATIONRS-CONFIGID-START
SCellActivationRS-ConfigId-r17 ::= INTEGER (1..maxNrofSCellActRS-r17)

-- TAG-SCELLACTIVATIONRS-CONFIGID-STOP
-- TAG-SCELLINDEX-START
SCellIndex ::= INTEGER (1..31)

-- TAG-SCHEDULINGREQUESTCONFIG-STOP
-- TAG-SCHEDULINGREQUESTID-START
SchedulingRequestId ::= INTEGER (0..7)

-- TAG-SCHEDULINGREQUESTRESOURCECONFIG-STOP
-- TAG-SCHEDULINGREQUESTRESOURCEID-START
SchedulingRequestResourceId ::= INTEGER (1..maxNrofSR-Resources)

-- TAG-SCHEDULINGREQUESTRESOURCEID-STOP
-- TAG-SCRAMBLINGID-START
ScramblingId ::= INTEGER (0..1023)

QFI ::= INTEGER (0..maxQFI)

PDU-SessionID ::= INTEGER (0..255)

-- TAG-SEARCHSPACEID-STOP
-- TAG-SEARCHSPACEZERO-START
SearchSpaceZero ::= INTEGER (0..15)

IntegrityProtAlgorithm ::= ENUMERATED { nia0(0), nia1(1), nia2(2), nia3(3), 
   spare4(4), spare3(5), spare2(6), spare1(7), ... }

CipheringAlgorithm ::= ENUMERATED { nea0(0), nea1(1), nea2(2), nea3(3), 
   spare4(4), spare3(5), spare2(6), spare1(7), ... }

DormancyGroupID-r16 ::= INTEGER (0..4)

-- TAG-SERVINGCELLCONFIGCOMMONSIB-STOP
-- TAG-SHORTI-RNTI-VALUE-START
ShortI-RNTI-Value ::= BIT STRING  (SIZE (24))

-- TAG-SHORTI-RNTI-VALUE-STOP
-- TAG-SHORTMAC-I-START
ShortMAC-I ::= BIT STRING  (SIZE (16))

-- TAG-SI-SCHEDULINGINFO-STOP
-- TAG-SKCOUNTER-START
SK-Counter ::= INTEGER (0..65535)

SlotFormatCombinationId ::= INTEGER (0..maxNrofSlotFormatCombinationsPerSet-1)

CO-Duration-r16 ::= INTEGER (0..1120)

CO-Duration-r17 ::= INTEGER (0..4480)

-- TAG-SPS-CONFIG-STOP
-- TAG-SPS-CONFIGINDEX-START
SPS-ConfigIndex-r16 ::= INTEGER (0..maxNrofSPS-Config-1-r16)

-- TAG-SPS-PUCCH-AN-LIST-STOP
-- TAG-SRB-IDENTITY-START
SRB-Identity ::= INTEGER (1..3)

SRB-Identity-v1700 ::= INTEGER (4)

AvailableSlotOffset-r17 ::= INTEGER (0..7)

SRS-PathlossReferenceRS-Id-r16 ::= INTEGER (0..maxNrofSRS-PathlossReferenceRS-1-r16)

SRS-ResourceSetId ::= INTEGER (0..maxNrofSRS-ResourceSets-1)

-- TAG-SRS-CONFIG-STOP
-- TAG-SRS-RSRP-RANGE-START
SRS-RSRP-Range-r16 ::= INTEGER (0..98)

TAG-Id ::= INTEGER (0..maxNrofTAGs-1)

-- TAG-TCI-UL-STATE-STOP
-- TAG-TCI-UL-STATEID-START
TCI-UL-StateId-r17 ::= INTEGER (0..maxUL-TCI-1-r17)

TDD-UL-DL-SlotIndex ::= INTEGER (0..maxNrofSlots-1)

-- TAG-TIMEALIGNMENTTIMER-STOP
-- TAG-TIMETOTRIGGER-START
TimeToTrigger ::= ENUMERATED { ms0(0), ms40(1), ms64(2), ms80(3), ms100(4), 
   ms128(5), ms160(6), ms256(7), ms320(8), ms480(9), ms512(10), ms640(11), 
   ms1024(12), ms1280(13), ms2560(14), ms5120(15) }

-- TAG-TIMETOTRIGGER-STOP
-- TAG-UAC-BARRINGINFOSETINDEX-START
UAC-BarringInfoSetIndex ::= INTEGER (1..maxBarringInfoSet)

-- TAG-UU-RELAYRLC-CHANNELCONFIG-STOP
-- TAG-UU-RELAYRLC-CHANNELID-START
Uu-RelayRLC-ChannelID-r17 ::= INTEGER (1..maxLC-ID)

FrequencyComponent-r17 ::= ENUMERATED { activeCarrier(0), configuredCarrier(1)
   , activeBWP(2), configuredBWP(3) }

-- TAG-ZP-CSI-RS-RESOURCESETID-STOP
-- TAG-ACCESSSTRATUMRELEASE-START
AccessStratumRelease ::= ENUMERATED { rel15(0), rel16(1), rel17(2), spare5(3), 
   spare4(4), spare3(5), spare2(6), spare1(7), ... }

ScalingFactorSidelink-r16 ::= ENUMERATED { f0p4(0), f0p75(1), f0p8(2), f1(3) }

IntraBandPowerClass-r16 ::= ENUMERATED { pc2(0), pc3(1), spare6(2), spare5(3), 
   spare4(4), spare3(5), spare2(6), spare1(7) }

SRS-SwitchingAffectedBandsNR-r17 ::= BIT STRING  (SIZE (1..maxSimultaneousBands))

-- TAG-BANDCOMBINATIONLISTSLDISCOVERY-STOP
-- TAG-CA-BANDWIDTHCLASSEUTRA-START
CA-BandwidthClassEUTRA ::= ENUMERATED { a(0), b(1), c(2), d(3), e(4), f(5), ...
    }

-- TAG-CA-BANDWIDTHCLASSEUTRA-STOP
-- TAG-CA-BANDWIDTHCLASSNR-START
-- R4 17-6: new CA BW Classes R2-R12
-- R4 17-7: new CA BW Classes V, W
CA-BandwidthClassNR ::= ENUMERATED { a(0), b(1), c(2), d(3), e(4), f(5), g(6), 
   h(7), i(8), j(9), k(10), l(11), m(12), n(13), o(14), p(15), q(16), ..., 
   r2-v1730(17), r3-v1730(18), r4-v1730(19), r5-v1730(20), r6-v1730(21), 
   r7-v1730(22), r8-v1730(23), r9-v1730(24), r10-v1730(25), r11-v1730(26), 
   r12-v1730(27), v-v1770(28), w-v1770(29) }

CA-BandwidthClassNR-r17 ::= ENUMERATED { r(0), s(1), t(2), u(3), ... }

-- TAG-FEATURESETCOMBINATION-STOP
-- TAG-FEATURESETCOMBINATIONID-START
FeatureSetCombinationId ::= INTEGER (0..maxFeatureSetCombinations)

-- TAG-FEATURESETDOWNLINK-STOP
-- TAG-FEATURESETDOWNLINKID-START
FeatureSetDownlinkId ::= INTEGER (0..maxDownlinkFeatureSets)

-- TAG-FEATURESETDOWNLINKPERCC-STOP
-- TAG-FEATURESETDOWNLINKPERCC-ID-START
FeatureSetDownlinkPerCC-Id ::= INTEGER (1..maxPerCC-FeatureSets)

-- TAG-FEATURESETDOWNLINKPERCC-ID-STOP
-- TAG-FEATURESETEUTRADOWNLINKID-START
FeatureSetEUTRA-DownlinkId ::= INTEGER (0..maxEUTRA-DL-FeatureSets)

-- TAG-FEATURESETEUTRADOWNLINKID-STOP
-- TAG-FEATURESETEUTRAUPLINKID-START
FeatureSetEUTRA-UplinkId ::= INTEGER (0..maxEUTRA-UL-FeatureSets)

-- TAG-FEATURESETUPLINK-STOP
-- TAG-FEATURESETUPLINKID-START
FeatureSetUplinkId ::= INTEGER (0..maxUplinkFeatureSets)

-- TAG-FEATURESETUPLINKPERCC-STOP
-- TAG-FEATURESETUPLINKPERCC-ID-START
FeatureSetUplinkPerCC-Id ::= INTEGER (1..maxPerCC-FeatureSets)

AggregatedBandwidth ::= ENUMERATED { mhz50(0), mhz100(1), mhz150(2), mhz200(3)
   , mhz250(4), mhz300(5), mhz350(6), mhz400(7), mhz450(8), mhz500(9), 
   mhz550(10), mhz600(11), mhz650(12), mhz700(13), mhz750(14), mhz800(15) }

-- TAG-FREQBANDLIST-STOP
-- TAG-FREQSEPARATIONCLASS-START
FreqSeparationClass ::= ENUMERATED { mhz800(0), mhz1200(1), mhz1400(2), ..., 
   mhz400-v1650(3), mhz600-v1650(4) }

FreqSeparationClassDL-v1620 ::= ENUMERATED { mhz1000(0), mhz1600(1), mhz1800(2)
   , mhz2000(3), mhz2200(4), mhz2400(5) }

FreqSeparationClassUL-v1620 ::= ENUMERATED { mhz1000(0) }

-- TAG-FREQSEPARATIONCLASS-STOP
-- TAG-FREQSEPARATIONCLASSDL-Only-START
FreqSeparationClassDL-Only-r16 ::= ENUMERATED { mhz200(0), mhz400(1), mhz600(2)
   , mhz800(3), mhz1000(4), mhz1200(5) }

SupportedBandUTRA-FDD-r16 ::= ENUMERATED { bandI(0), bandII(1), bandIII(2), 
   bandIV(3), bandV(4), bandVI(5), bandVII(6), bandVIII(7), bandIX(8), bandX(9)
   , bandXI(10), bandXII(11), bandXIII(12), bandXIV(13), bandXV(14), 
   bandXVI(15), bandXVII(16), bandXVIII(17), bandXIX(18), bandXX(19), 
   bandXXI(20), bandXXII(21), bandXXIII(22), bandXXIV(23), bandXXV(24), 
   bandXXVI(25), bandXXVII(26), bandXXVIII(27), bandXXIX(28), bandXXX(29), 
   bandXXXI(30), bandXXXII(31) }

-- TAG-MEASANDMOBPARAMETERSMRDC-STOP
-- TAG-MIMO-LAYERS-START
MIMO-LayersDL ::= ENUMERATED { twoLayers(0), fourLayers(1), eightLayers(2) }

MIMO-LayersUL ::= ENUMERATED { oneLayer(0), twoLayers(1), fourLayers(2) }

-- TAG-MIMO-PARAMETERSPERBAND-STOP
-- TAG-MODULATIONORDER-START
ModulationOrder ::= ENUMERATED { bpsk-halfpi(0), bpsk(1), qpsk(2), qam16(3), 
   qam64(4), qam256(5) }

NumberOfCarriers ::= INTEGER (1..16)

-- TAG-PRS-PROCESSINGCAPABILITYOUTSIDEMGINPPWPERType-STOP
-- TAG-RAT-TYPE-START
RAT-Type ::= ENUMERATED { nr(0), eutra-nr(1), eutra(2), utra-fdd-v1610(3), ...
    }

-- TAG-SIDELINKPARAMETERS-STOP
-- TAG-SIMULTANEOUSRXTXPERBANDPAIR-START
SimultaneousRxTxPerBandPair ::= BIT STRING  (SIZE (3..496))

-- TAG-SHAREDSPECTRUMCHACCESSPARAMSPERBAND-STOP
-- TAG-ABSOLUTETIMEINFO-START
AbsoluteTimeInfo-r16 ::= BIT STRING  (SIZE (48))

BT-Name-r16 ::= OCTET STRING (SIZE (1..248))

-- TAG-BTNAMELIST-STOP
-- TAG-DEDICATEDINFOF1C-START
DedicatedInfoF1c-r17 ::= OCTET STRING

-- TAG-IABIPADDRESS-STOP
-- TAG-IABIPADDRESSINDEX-START
IAB-IP-AddressIndex-r16 ::= INTEGER (1..maxIAB-IP-Address-r16)

-- TAG-IABIPADDRESSINDEX-STOP
-- TAG-IAB-IP-USAGE-START
IAB-IP-Usage-r16 ::= ENUMERATED { f1-C(0), f1-U(1), non-F1(2), spare(3) }

-- TAG-IAB-IP-USAGE-STOP
-- TAG-LOGGINGDURATION-START
LoggingDuration-r16 ::= ENUMERATED { min10(0), min20(1), min40(2), min60(3), 
   min90(4), min120(5), spare2(6), spare1(7) }

-- TAG-LOGGINGDURATION-STOP
-- TAG-LOGGINGINTERVAL-START
LoggingInterval-r16 ::= ENUMERATED { ms320(0), ms640(1), ms1280(2), ms2560(3), 
   ms5120(4), ms10240(5), ms20480(6), ms30720(7), ms40960(8), ms61440(9), 
   infinity(10) }

WLAN-RSSI-Range-r16 ::= INTEGER (0..141)

-- TAG-LOGMEASRESULTLISTWLAN-STOP
-- TAG-MEASCONFIGAPPLAYERID-START
MeasConfigAppLayerId-r17 ::= INTEGER (0..maxNrofAppLayerMeas-1-r17)

-- TAG-OTHERCONFIG-STOP
-- TAG-PHYSCELLIDUTRA-FDD-START
PhysCellIdUTRA-FDD-r16 ::= INTEGER (0..511)

-- TAG-PHYSCELLIDUTRA-FDD-STOP
-- TAG-RRC-TRANSACTIONIDENTIFIER-START
RRC-TransactionIdentifier ::= INTEGER (0..3)

-- TAG-UE-MeasurementsAvailable-STOP
-- TAG-UTRA-FDD-Q-OFFSETRANGE-START
UTRA-FDD-Q-OffsetRange-r16 ::= ENUMERATED { dB-24(0), dB-22(1), dB-20(2), 
   dB-18(3), dB-16(4), dB-14(5), dB-12(6), dB-10(7), dB-8(8), dB-6(9), dB-5(10)
   , dB-4(11), dB-3(12), dB-2(13), dB-1(14), dB0(15), dB1(16), dB2(17), dB3(18)
   , dB4(19), dB5(20), dB6(21), dB8(22), dB10(23), dB12(24), dB14(25), dB16(26)
   , dB18(27), dB20(28), dB22(29), dB24(30) }

WLAN-Name-r16 ::= OCTET STRING (SIZE (1..32))

SL-ResourcePoolID-r16 ::= INTEGER (1..maxNrofPoolID-r16)

SL-TxConfigIndex-r16 ::= INTEGER (0..maxTxConfig-1-r16)

SL-CBR-r16 ::= INTEGER (0..100)

SL-DestinationIndex-r16 ::= INTEGER (0..maxNrofSL-Dest-1-r16)

SL-ConfigIndexCG-r16 ::= INTEGER (0..maxNrofCG-SL-1-r16)

-- TAG-SL-CONFIGUREDGRANTCONFIG-STOP
-- TAG-SL-DESTINATIONIDENTITY-START
SL-DestinationIdentity-r16 ::= BIT STRING  (SIZE (24))

SL-Freq-Id-r16 ::= INTEGER (1..maxNrofFreqSL-r16)

SL-MeasId-r16 ::= INTEGER (1..maxNrofSL-MeasId-r16)

SL-MeasObjectId-r16 ::= INTEGER (1..maxNrofSL-ObjectId-r16)

-- TAG-SL-PSSCH-TXCONFIGLIST-STOP
-- TAG-SL-QOS-FLOWIDENTITY-START
SL-QoS-FlowIdentity-r16 ::= INTEGER (1..maxNrofSL-QFIs-r16)

SL-ReportConfigId-r16 ::= INTEGER (1..maxNrofSL-ReportConfigId-r16)

SL-RS-Type-r16 ::= ENUMERATED { dmrs(0), spare3(1), spare2(2), spare1(3) }

SL-BetaOffsets-r16 ::= INTEGER (0..31)

-- TAG-SL-RLC-BEARERCONFIG-STOP
-- TAG-SL-RLC-BEARERCONFIGINDEX-START
SL-RLC-BearerConfigIndex-r16 ::= INTEGER (1..maxSL-LCID-r16)

-- TAG-SL-RLC-CHANNEL-CONFIG-STOP
-- TAG-SL-RLC-CHANNELID-START
SL-RLC-ChannelID-r17 ::= INTEGER (1..maxSL-LCID-r16)

-- TAG-SL-SERVINGCELLINFO-STOP
-- TAG-SL-SOURCEIDENTITY-START
SL-SourceIdentity-r17 ::= BIT STRING  (SIZE (24))

SL-RSRP-Range-r16 ::= INTEGER (0..13)

SL-Thres-RSRP-r16 ::= INTEGER (0..66)

-- TAG-SL-TXPOWER-STOP
-- TAG-SL-TYPETXSYNC-START
SL-TypeTxSync-r16 ::= ENUMERATED { gnss(0), gnbEnb(1), ue(2) }

-- TAG-SL-ZONECONFIG-STOP
-- TAG-SLRB-UU-CONFIGINDEX-START
SLRB-Uu-ConfigIndex-r16 ::= INTEGER (1..maxNrofSLRB-r16)

DRX-ConfigPTM-Index-r17 ::= INTEGER (0..maxNrofDRX-ConfigPTM-1-r17)

PDSCH-ConfigIndex-r17 ::= INTEGER (0..maxNrofPDSCH-ConfigPTM-1-r17)

MTCH-SSB-MappingWindowIndex-r17 ::= INTEGER (0..maxNrofMTCH-SSB-MappingWindow-1-r17)

-- TAG-PDCCH-CONFIGCOMMON-STOP
-- TAG-PDCCH-CONFIGSIB1-START
PDCCH-ConfigSIB1 ::= SEQUENCE {
   controlResourceSetZero [0] ControlResourceSetZero,
   searchSpaceZero [1] SearchSpaceZero
}

-- TAG-MEASUREMENTREPORTAPPLAYER-STOP
-- TAG-MIB-START
MIB ::= SEQUENCE {
   systemFrameNumber [0] BIT STRING  (SIZE (6)),
   subCarrierSpacingCommon [1] ENUMERATED { scs15or60(0), scs30or120(1) },
   ssb-SubcarrierOffset [2] INTEGER (0..15),
   dmrs-TypeA-Position [3] ENUMERATED { pos2(0), pos3(1) },
   pdcch-ConfigSIB1 [4] PDCCH-ConfigSIB1,
   cellBarred [5] ENUMERATED { barred(0), notBarred(1) },
   intraFreqReselection [6] ENUMERATED { allowed(0), notAllowed(1) },
   spare [7] BIT STRING  (SIZE (1))
}

BCCH-BCH-MessageType ::= CHOICE {
   mib [0] MIB,
   messageClassExtension [1] SEQUENCE {

   }
}

-- TAG-NR-RRC-DEFINITIONS-STOP
-- TAG-BCCH-BCH-MESSAGE-START
BCCH-BCH-Message ::= SEQUENCE {
   message [0] EXPLICIT BCCH-BCH-MessageType
}

PLMN-IdentityInfo ::= SEQUENCE {
   plmn-IdentityList [0] SEQUENCE (SIZE (1..maxPLMN)) OF PLMN-Identity,
   trackingAreaCode [1] TrackingAreaCode OPTIONAL, -- Need R
   ranac [2] RAN-AreaCode OPTIONAL, -- Need R
   cellIdentity [3] CellIdentity,
   cellReservedForOperatorUse [4] ENUMERATED { reserved(0), notReserved(1) },
   ...,
   [[
      iab-Support-r16 [5] ENUMERATED { true(0) } OPTIONAL
   ]],
   [[
      trackingAreaList-r17 [6] SEQUENCE (SIZE (1..maxTAC-r17)) OF TrackingAreaCode
          OPTIONAL,
      gNB-ID-Length-r17 [7] INTEGER (22..32) OPTIONAL
   ]]
}

-- TAG-PLMN-IDENTITY-STOP
-- TAG-PLMN-IDENTITYINFOLIST-START
PLMN-IdentityInfoList ::= SEQUENCE (SIZE (1..maxPLMN)) OF PLMN-IdentityInfo

CAG-IdentityInfo-r16 ::= SEQUENCE {
   cag-Identity-r16 [0] BIT STRING  (SIZE (32)),
   manualCAGselectionAllowed-r16 [1] ENUMERATED { true(0) } OPTIONAL -- Need R
}

-- TAG-NONCELLDEFININGSSB-STOP
-- TAG-NPN-IDENTITY-START
NPN-Identity-r16 ::= CHOICE {
   pni-npn-r16 [0] SEQUENCE {
      plmn-Identity-r16 [0] PLMN-Identity,
      cag-IdentityList-r16 [1] SEQUENCE (SIZE (1..maxNPN-r16)) OF CAG-IdentityInfo-r16
   },
   snpn-r16 [1] SEQUENCE {
      plmn-Identity-r16 [0] PLMN-Identity,
      nid-List-r16 [1] SEQUENCE (SIZE (1..maxNPN-r16)) OF NID-r16
   }
}

NPN-IdentityInfo-r16 ::= SEQUENCE {
   npn-IdentityList-r16 [0] SEQUENCE (SIZE (1..maxNPN-r16)) OF NPN-Identity-r16,
   trackingAreaCode-r16 [1] TrackingAreaCode,
   ranac-r16 [2] RAN-AreaCode OPTIONAL, -- Need R
   cellIdentity-r16 [3] CellIdentity,
   cellReservedForOperatorUse-r16 [4] ENUMERATED { reserved(0), notReserved(1)
       },
   iab-Support-r16 [5] ENUMERATED { true(0) } OPTIONAL,
   ...,
   [[
      gNB-ID-Length-r17 [6] INTEGER (22..32) OPTIONAL
   ]]
}

-- TAG-NPN-IDENTITY-STOP
-- TAG-NPN-IDENTITYINFOLIST-START
NPN-IdentityInfoList-r16 ::= SEQUENCE (SIZE (1..maxNPN-r16)) OF NPN-IdentityInfo-r16

SNPN-AccessInfo-r17 ::= SEQUENCE {
   extCH-Supported-r17 [0] ENUMERATED { true(0) } OPTIONAL, -- Need R
   extCH-WithoutConfigAllowed-r17 [1] ENUMERATED { true(0) } OPTIONAL, -- Need R
   onboardingEnabled-r17 [2] ENUMERATED { true(0) } OPTIONAL, -- Need R
   imsEmergencySupportForSNPN-r17 [3] ENUMERATED { true(0) } OPTIONAL -- Need R
}

-- TAG-CANDIDATEBEAMRS-STOP
-- TAG-CELLACCESSRELATEDINFO-START
CellAccessRelatedInfo ::= SEQUENCE {
   plmn-IdentityInfoList [0] PLMN-IdentityInfoList,
   cellReservedForOtherUse [1] ENUMERATED { true(0) } OPTIONAL,
   ...,
   [[
      cellReservedForFutureUse-r16 [2] ENUMERATED { true(0) } OPTIONAL,
      npn-IdentityInfoList-r16 [3] NPN-IdentityInfoList-r16 OPTIONAL
   ]],
   [[
      snpn-AccessInfoList-r17 [4] SEQUENCE (SIZE (1..maxNPN-r16)) OF SNPN-AccessInfo-r17
          OPTIONAL
   ]]
}

-- TAG-CONFIGUREDGRANTCONFIGINDEXMAC-STOP
-- TAG-CONNESTFAILURECONTROL-START
ConnEstFailureControl ::= SEQUENCE {
   connEstFailCount [0] ENUMERATED { n1(0), n2(1), n3(2), n4(3) },
   connEstFailOffsetValidity [1] ENUMERATED { s30(0), s60(1), s120(2), s240(3)
      , s300(4), s420(5), s600(6), s900(7) },
   connEstFailOffset [2] INTEGER (0..15) OPTIONAL -- Need S
}

SIB-TypeInfo ::= SEQUENCE {
   type [0] ENUMERATED { sibType2(0), sibType3(1), sibType4(2), sibType5(3), 
      sibType6(4), sibType7(5), sibType8(6), sibType9(7), sibType10-v1610(8), 
      sibType11-v1610(9), sibType12-v1610(10), sibType13-v1610(11), 
      sibType14-v1610(12), spare3(13), spare2(14), spare1(15), ... },
   valueTag [1] INTEGER (0..31) OPTIONAL, -- Cond SIB-TYPE
   areaScope [2] ENUMERATED { true(0) } OPTIONAL -- Need S
}

SIB-Mapping ::= SEQUENCE (SIZE (1..maxSIB)) OF SIB-TypeInfo

SchedulingInfo ::= SEQUENCE {
   si-BroadcastStatus [0] ENUMERATED { broadcasting(0), notBroadcasting(1) },
   si-Periodicity [1] ENUMERATED { rf8(0), rf16(1), rf32(2), rf64(3), rf128(4)
      , rf256(5), rf512(6) },
   sib-MappingInfo [2] SIB-Mapping
}

-- TAG-RACH-CONFIGDEDICATED-STOP
-- TAG-RACH-CONFIGGENERIC-START
RACH-ConfigGeneric ::= SEQUENCE {
   prach-ConfigurationIndex [0] INTEGER (0..255),
   msg1-FDM [1] ENUMERATED { one(0), two(1), four(2), eight(3) },
   msg1-FrequencyStart [2] INTEGER (0..maxNrofPhysicalResourceBlocks-1),
   zeroCorrelationZoneConfig [3] INTEGER (0..15),
   preambleReceivedTargetPower [4] INTEGER (-202..-60),
   preambleTransMax [5] ENUMERATED { n3(0), n4(1), n5(2), n6(3), n7(4), n8(5), 
      n10(6), n20(7), n50(8), n100(9), n200(10) },
   powerRampingStep [6] ENUMERATED { dB0(0), dB2(1), dB4(2), dB6(3) },
   ra-ResponseWindow [7] ENUMERATED { sl1(0), sl2(1), sl4(2), sl8(3), sl10(4), 
      sl20(5), sl40(6), sl80(7) },
   ...,
   [[
      prach-ConfigurationPeriodScaling-IAB-r16 [8] ENUMERATED { scf1(0), 
         scf2(1), scf4(2), scf8(3), scf16(4), scf32(5), scf64(6) } OPTIONAL,
      prach-ConfigurationFrameOffset-IAB-r16 [9] INTEGER (0..63) OPTIONAL,
      prach-ConfigurationSOffset-IAB-r16 [10] INTEGER (0..39) OPTIONAL,
      ra-ResponseWindow-v1610 [11] ENUMERATED { sl60(0), sl160(1) } OPTIONAL,
      prach-ConfigurationIndex-v1610 [12] INTEGER (256..262) OPTIONAL
   ]],
   [[
      ra-ResponseWindow-v1700 [13] ENUMERATED { sl240(0), sl320(1), sl640(2), 
         sl960(3), sl1280(4), sl1920(5), sl2560(6) } OPTIONAL
   ]]
}

SI-RequestResources ::= SEQUENCE {
   ra-PreambleStartIndex [0] INTEGER (0..63),
   ra-AssociationPeriodIndex [1] INTEGER (0..15) OPTIONAL, -- Need R
   ra-ssb-OccasionMaskIndex [2] INTEGER (0..15) OPTIONAL -- Need R
}

-- TAG-SINR-RANGE-STOP
-- TAG-SI-REQUESTCONFIG-START
SI-RequestConfig ::= SEQUENCE {
   rach-OccasionsSI [0] SEQUENCE {
      rach-ConfigSI [0] RACH-ConfigGeneric,
      ssb-perRACH-Occasion [1] ENUMERATED { oneEighth(0), oneFourth(1), 
         oneHalf(2), one(3), two(4), four(5), eight(6), sixteen(7) }
   } OPTIONAL, -- Need R
   si-RequestPeriod [1] ENUMERATED { one(0), two(1), four(2), six(3), eight(4)
      , ten(5), twelve(6), sixteen(7) } OPTIONAL, -- Need R
   si-RequestResources [2] SEQUENCE (SIZE (1..maxSI-Message)) OF SI-RequestResources
}

-- TAG-SI-REQUESTCONFIG-STOP
-- TAG-SI-SCHEDULINGINFO-START
SI-SchedulingInfo ::= SEQUENCE {
   schedulingInfoList [0] SEQUENCE (SIZE (1..maxSI-Message)) OF SchedulingInfo,
   si-WindowLength [1] ENUMERATED { s5(0), s10(1), s20(2), s40(3), s80(4), 
      s160(5), s320(6), s640(7), s1280(8), s2560-v1710(9), s5120-v1710(10) },
   si-RequestConfig [2] SI-RequestConfig OPTIONAL, -- Cond MSG-1
   si-RequestConfigSUL [3] SI-RequestConfig OPTIONAL, -- Cond SUL-MSG-1
   systemInformationAreaID [4] BIT STRING  (SIZE (24)) OPTIONAL,
   ...
}

-- TAG-SCRAMBLINGID-STOP
-- TAG-SCS-SPECIFICCARRIER-START
SCS-SpecificCarrier ::= SEQUENCE {
   offsetToCarrier [0] INTEGER (0..2199),
   subcarrierSpacing [1] SubcarrierSpacing,
   carrierBandwidth [2] INTEGER (1..maxNrofPhysicalResourceBlocks),
   ...,
   [[
      txDirectCurrentLocation [3] INTEGER (0..4095) OPTIONAL
   ]]
}

-- TAG-FREQUENCYINFODL-STOP
-- TAG-FREQUENCYINFODL-SIB-START
FrequencyInfoDL-SIB ::= SEQUENCE {
   frequencyBandList [0] MultiFrequencyBandListNR-SIB,
   offsetToPointA [1] INTEGER (0..2199),
   scs-SpecificCarrierList [2] SEQUENCE (SIZE (1..maxSCSs)) OF SCS-SpecificCarrier
}

-- TAG-PDCCH-CONFIG-STOP
-- TAG-PDCCH-CONFIGCOMMON-START
PDCCH-ConfigCommon ::= SEQUENCE {
   controlResourceSetZero [0] ControlResourceSetZero OPTIONAL, -- Cond InitialBWP-Only
   commonControlResourceSet [1] ControlResourceSet OPTIONAL, -- Need R
   searchSpaceZero [2] SearchSpaceZero OPTIONAL, -- Cond InitialBWP-Only
   commonSearchSpaceList [3] SEQUENCE (SIZE (1..4)) OF SearchSpace OPTIONAL, -- Need R
   searchSpaceSIB1 [4] SearchSpaceId OPTIONAL, -- Need S
   searchSpaceOtherSystemInformation [5] SearchSpaceId OPTIONAL, -- Need S
   pagingSearchSpace [6] SearchSpaceId OPTIONAL, -- Need S
   ra-SearchSpace [7] SearchSpaceId OPTIONAL,
   ...,
   [[
      firstPDCCH-MonitoringOccasionOfPO [8] EXPLICIT CHOICE {
         sCS15KHZoneT [0] SEQUENCE (SIZE (1..maxPO-perPF)) OF INTEGER (0..139),
         sCS30KHZoneT-SCS15KHZhalfT [1] SEQUENCE (SIZE (1..maxPO-perPF)) OF INTEGER (0..279),
         sCS60KHZoneT-SCS30KHZhalfT-SCS15KHZquarterT [2] SEQUENCE (SIZE (1..maxPO-perPF)
            ) OF INTEGER (0..559),
         sCS120KHZoneT-SCS60KHZhalfT-SCS30KHZquarterT-SCS15KHZoneEighthT [3] 
            SEQUENCE (SIZE (1..maxPO-perPF)) OF INTEGER (0..1119),
         sCS120KHZhalfT-SCS60KHZquarterT-SCS30KHZoneEighthT-SCS15KHZoneSixteenthT 
            [4] SEQUENCE (SIZE (1..maxPO-perPF)) OF INTEGER (0..2239),
         sCS120KHZquarterT-SCS60KHZoneEighthT-SCS30KHZoneSixteenthT [5] 
            SEQUENCE (SIZE (1..maxPO-perPF)) OF INTEGER (0..4479),
         sCS120KHZoneEighthT-SCS60KHZoneSixteenthT [6] SEQUENCE (SIZE (1..maxPO-perPF)) OF 
            INTEGER (0..8959),
         sCS120KHZoneSixteenthT [7] SEQUENCE (SIZE (1..maxPO-perPF)) OF INTEGER (0..17919)
      } OPTIONAL
   ]],
   [[
      commonSearchSpaceListExt-r16 [9] SEQUENCE (SIZE (1..4)) OF 
         SearchSpaceExt-r16 OPTIONAL
   ]],
   [[
      sdt-SearchSpace-r17 [10] EXPLICIT CHOICE {
         newSearchSpace [0] SearchSpace,
         existingSearchSpace [1] SearchSpaceId
      } OPTIONAL,
      searchSpaceMCCH-r17 [11] SearchSpaceId OPTIONAL,
      searchSpaceMTCH-r17 [12] SearchSpaceId OPTIONAL,
      commonSearchSpaceListExt2-r17 [13] SEQUENCE (SIZE (1..4)) OF 
         SearchSpaceExt-v1700 OPTIONAL,
      firstPDCCH-MonitoringOccasionOfPO-v1710 [14] EXPLICIT CHOICE {
         sCS480KHZoneEighthT [0] SEQUENCE (SIZE (1..maxPO-perPF)) OF INTEGER (0..35839),
         sCS480KHZoneSixteenthT [1] SEQUENCE (SIZE (1..maxPO-perPF)) OF INTEGER (0..71679)
      } OPTIONAL,
      pei-ConfigBWP-r17 [15] SEQUENCE {
         pei-SearchSpace-r17 [0] SearchSpaceId,
         firstPDCCH-MonitoringOccasionOfPEI-O-r17 [1] EXPLICIT CHOICE {
            sCS15KHZoneT [0] SEQUENCE (SIZE (1..maxPEI-perPF-r17)) OF INTEGER (0..139),
            sCS30KHZoneT-SCS15KHZhalfT [1] SEQUENCE (SIZE (1..maxPEI-perPF-r17)) OF INTEGER (0..279)
               ,
            sCS60KHZoneT-SCS30KHZhalfT-SCS15KHZquarterT [2] SEQUENCE (SIZE (1..maxPEI-perPF-r17)
               ) OF INTEGER (0..559),
            sCS120KHZoneT-SCS60KHZhalfT-SCS30KHZquarterT-SCS15KHZoneEighthT 
               [3] SEQUENCE (SIZE (1..maxPEI-perPF-r17)) OF INTEGER (0..1119),
            sCS120KHZhalfT-SCS60KHZquarterT-SCS30KHZoneEighthT-SCS15KHZoneSixteenthT 
               [4] SEQUENCE (SIZE (1..maxPEI-perPF-r17)) OF INTEGER (0..2239),
            sCS480KHZoneT-SCS120KHZquarterT-SCS60KHZoneEighthT-SCS30KHZoneSixteenthT 
               [5] SEQUENCE (SIZE (1..maxPEI-perPF-r17)) OF INTEGER (0..4479),
            sCS480KHZhalfT-SCS120KHZoneEighthT-SCS60KHZoneSixteenthT [6] 
               SEQUENCE (SIZE (1..maxPEI-perPF-r17)) OF INTEGER (0..8959),
            sCS480KHZquarterT-SCS120KHZoneSixteenthT [7] SEQUENCE (SIZE (1..maxPEI-perPF-r17)
               ) OF INTEGER (0..17919),
            sCS480KHZoneEighthT [8] SEQUENCE (SIZE (1..maxPEI-perPF-r17)) OF INTEGER (0..35839),
            sCS480KHZoneSixteenthT [9] SEQUENCE (SIZE (1..maxPEI-perPF-r17)) OF INTEGER (0..71679)
         }
      } OPTIONAL
   ]],
   [[
      followUnifiedTCI-State-v1720 [16] ENUMERATED { enabled(0) } OPTIONAL
   ]]
}

-- TAG-PDSCH-CONFIG-STOP
-- TAG-PDSCH-CONFIGCOMMON-START
PDSCH-ConfigCommon ::= SEQUENCE {
   pdsch-TimeDomainAllocationList [0] PDSCH-TimeDomainResourceAllocationList
       OPTIONAL,
   ...
}

-- TAG-BWP-DOWNLINK-STOP
-- TAG-BWP-DOWNLINKCOMMON-START
BWP-DownlinkCommon ::= SEQUENCE {
   genericParameters [0] BWP,
   pdcch-ConfigCommon [1] EXPLICIT CHOICE {
      release [0] NULL,
      setup [1] EXPLICIT PDCCH-ConfigCommon
   } OPTIONAL, -- Need M
   pdsch-ConfigCommon [2] EXPLICIT CHOICE {
      release [0] NULL,
      setup [1] EXPLICIT PDSCH-ConfigCommon
   } OPTIONAL,
   ...
}

BCCH-Config ::= SEQUENCE {
   modificationPeriodCoeff [0] ENUMERATED { n2(0), n4(1), n8(2), n16(3) },
   ...
}

PCCH-Config ::= SEQUENCE {
   defaultPagingCycle [0] PagingCycle,
   nAndPagingFrameOffset [1] EXPLICIT CHOICE {
      oneT [0] NULL,
      halfT [1] INTEGER (0..1),
      quarterT [2] INTEGER (0..3),
      oneEighthT [3] INTEGER (0..7),
      oneSixteenthT [4] INTEGER (0..15)
   },
   ns [2] ENUMERATED { four(0), two(1), one(2) },
   firstPDCCH-MonitoringOccasionOfPO [3] EXPLICIT CHOICE {
      sCS15KHZoneT [0] SEQUENCE (SIZE (1..maxPO-perPF)) OF INTEGER (0..139),
      sCS30KHZoneT-SCS15KHZhalfT [1] SEQUENCE (SIZE (1..maxPO-perPF)) OF INTEGER (0..279),
      sCS60KHZoneT-SCS30KHZhalfT-SCS15KHZquarterT [2] SEQUENCE (SIZE (1..maxPO-perPF)) OF 
         INTEGER (0..559),
      sCS120KHZoneT-SCS60KHZhalfT-SCS30KHZquarterT-SCS15KHZoneEighthT [3] 
         SEQUENCE (SIZE (1..maxPO-perPF)) OF INTEGER (0..1119),
      sCS120KHZhalfT-SCS60KHZquarterT-SCS30KHZoneEighthT-SCS15KHZoneSixteenthT 
         [4] SEQUENCE (SIZE (1..maxPO-perPF)) OF INTEGER (0..2239),
      sCS480KHZoneT-SCS120KHZquarterT-SCS60KHZoneEighthT-SCS30KHZoneSixteenthT 
         [5] SEQUENCE (SIZE (1..maxPO-perPF)) OF INTEGER (0..4479),
      sCS480KHZhalfT-SCS120KHZoneEighthT-SCS60KHZoneSixteenthT [6] SEQUENCE (
         SIZE (1..maxPO-perPF)) OF INTEGER (0..8959),
      sCS480KHZquarterT-SCS120KHZoneSixteenthT [7] SEQUENCE (SIZE (1..maxPO-perPF)) OF 
         INTEGER (0..17919)
   } OPTIONAL,
   ...,
   [[
      nrofPDCCH-MonitoringOccasionPerSSB-InPO-r16 [4] INTEGER (2..4) OPTIONAL
   ]],
   [[
      ranPagingInIdlePO-r17 [5] ENUMERATED { true(0) } OPTIONAL,
      firstPDCCH-MonitoringOccasionOfPO-v1710 [6] EXPLICIT CHOICE {
         sCS480KHZoneEighthT [0] SEQUENCE (SIZE (1..maxPO-perPF)) OF INTEGER (0..35839),
         sCS480KHZoneSixteenthT [1] SEQUENCE (SIZE (1..maxPO-perPF)) OF INTEGER (0..71679)
      } OPTIONAL
   ]]
}

SubgroupConfig-r17 ::= SEQUENCE {
   subgroupsNumPerPO-r17 [0] INTEGER (1..maxNrofPagingSubgroups-r17),
   subgroupsNumForUEID-r17 [1] INTEGER (1..maxNrofPagingSubgroups-r17) OPTIONAL,
   ...
}

PEI-Config-r17 ::= SEQUENCE {
   po-NumPerPEI-r17 [0] ENUMERATED { po1(0), po2(1), po4(2), po8(3) },
   payloadSizeDCI-2-7-r17 [1] INTEGER (1..maxDCI-2-7-Size-r17),
   pei-FrameOffset-r17 [2] INTEGER (0..16),
   subgroupConfig-r17 [3] SubgroupConfig-r17,
   lastUsedCellOnly-r17 [4] ENUMERATED { true(0) } OPTIONAL,
   ...
}

-- TAG-DOWNLINKCONFIGCOMMON-STOP
-- TAG-DOWNLINKCONFIGCOMMONSIB-START
DownlinkConfigCommonSIB ::= SEQUENCE {
   frequencyInfoDL [0] FrequencyInfoDL-SIB,
   initialDownlinkBWP [1] BWP-DownlinkCommon,
   bcch-Config [2] BCCH-Config,
   pcch-Config [3] PCCH-Config,
   ...,
   [[
      pei-Config-r17 [4] PEI-Config-r17 OPTIONAL,
      initialDownlinkBWP-RedCap-r17 [5] BWP-DownlinkCommon OPTIONAL
   ]]
}

-- TAG-FREQUENCYINFOUL-STOP
-- TAG-FREQUENCYINFOUL-SIB-START
FrequencyInfoUL-SIB ::= SEQUENCE {
   frequencyBandList [0] MultiFrequencyBandListNR-SIB OPTIONAL, -- Cond FDD-OrSUL
   absoluteFrequencyPointA [1] ARFCN-ValueNR OPTIONAL, -- Cond FDD-OrSUL
   scs-SpecificCarrierList [2] SEQUENCE (SIZE (1..maxSCSs)) OF SCS-SpecificCarrier,
   p-Max [3] P-Max OPTIONAL, -- Need S
   frequencyShift7p5khz [4] ENUMERATED { true(0) } OPTIONAL,
   ...
}

-- TAG-RACH-CONFIGGENERICTWOSTEPRA-STOP
-- TAG-RA-PRIORITIZATION-START
RA-Prioritization ::= SEQUENCE {
   powerRampingStepHighPriority [0] ENUMERATED { dB0(0), dB2(1), dB4(2), dB6(3)
       },
   scalingFactorBI [1] ENUMERATED { zero(0), dot25(1), dot5(2), dot75(3) }
       OPTIONAL,
   ...
}

RA-PrioritizationSliceInfo-r17 ::= SEQUENCE {
   nsag-ID-List-r17 [0] SEQUENCE (SIZE (1..maxSliceInfo-r17)) OF NSAG-ID-r17,
   ra-Prioritization-r17 [1] RA-Prioritization,
   ...
}

RA-PrioritizationSliceInfoList-r17 ::= SEQUENCE (SIZE (1..maxSliceInfo-r17)) OF 
   RA-PrioritizationSliceInfo-r17

-- TAG-RA-PRIORITIZATION-STOP
-- TAG-RA-PRIORITIZATIONFORSLICING-START
RA-PrioritizationForSlicing-r17 ::= SEQUENCE {
   ra-PrioritizationSliceInfoList-r17 [0] RA-PrioritizationSliceInfoList-r17,
   ...
}

NSAG-List-r17 ::= SEQUENCE (SIZE (1..maxSliceInfo-r17)) OF NSAG-ID-r17

-- TAG-EPHEMERISINFO-STOP
-- TAG-FEATURECOMBINATION-START
FeatureCombination-r17 ::= SEQUENCE {
   redCap-r17 [0] ENUMERATED { true(0) } OPTIONAL, -- Need R
   smallData-r17 [1] ENUMERATED { true(0) } OPTIONAL, -- Need R
   nsag-r17 [2] NSAG-List-r17 OPTIONAL, -- Need R
   msg3-Repetitions-r17 [3] ENUMERATED { true(0) } OPTIONAL, -- Need R
   spare4 [4] ENUMERATED { true(0) } OPTIONAL, -- Need R
   spare3 [5] ENUMERATED { true(0) } OPTIONAL, -- Need R
   spare2 [6] ENUMERATED { true(0) } OPTIONAL, -- Need R
   spare1 [7] ENUMERATED { true(0) } OPTIONAL -- Need R
}

MsgA-DMRS-Config-r16 ::= SEQUENCE {
   msgA-DMRS-AdditionalPosition-r16 [0] ENUMERATED { pos0(0), pos1(1), pos3(2)
       } OPTIONAL, -- Need S
   msgA-MaxLength-r16 [1] ENUMERATED { len2(0) } OPTIONAL, -- Need S
   msgA-PUSCH-DMRS-CDM-Group-r16 [2] INTEGER (0..1) OPTIONAL, -- Need S
   msgA-PUSCH-NrofPorts-r16 [3] INTEGER (0..1) OPTIONAL, -- Need S
   msgA-ScramblingID0-r16 [4] INTEGER (0..65535) OPTIONAL, -- Need S
   msgA-ScramblingID1-r16 [5] INTEGER (0..65535) OPTIONAL -- Need S
}

MsgA-PUSCH-Resource-r16 ::= SEQUENCE {
   msgA-MCS-r16 [0] INTEGER (0..15),
   nrofSlotsMsgA-PUSCH-r16 [1] INTEGER (1..4),
   nrofMsgA-PO-PerSlot-r16 [2] ENUMERATED { one(0), two(1), three(2), six(3) },
   msgA-PUSCH-TimeDomainOffset-r16 [3] INTEGER (1..32),
   msgA-PUSCH-TimeDomainAllocation-r16 [4] INTEGER (1..maxNrofUL-Allocations) OPTIONAL, -- Need S
   startSymbolAndLengthMsgA-PO-r16 [5] INTEGER (0..127) OPTIONAL, -- Need S
   mappingTypeMsgA-PUSCH-r16 [6] ENUMERATED { typeA(0), typeB(1) } OPTIONAL, -- Need S
   guardPeriodMsgA-PUSCH-r16 [7] INTEGER (0..3) OPTIONAL, -- Need R
   guardBandMsgA-PUSCH-r16 [8] INTEGER (0..1),
   frequencyStartMsgA-PUSCH-r16 [9] INTEGER (0..maxNrofPhysicalResourceBlocks-1),
   nrofPRBs-PerMsgA-PO-r16 [10] INTEGER (1..32),
   nrofMsgA-PO-FDM-r16 [11] ENUMERATED { one(0), two(1), four(2), eight(3) },
   msgA-IntraSlotFrequencyHopping-r16 [12] ENUMERATED { enabled(0) } OPTIONAL, -- Need R
   msgA-HoppingBits-r16 [13] BIT STRING  (SIZE (2)) OPTIONAL, -- Cond FreqHopConfigured
   msgA-DMRS-Config-r16 [14] MsgA-DMRS-Config-r16,
   nrofDMRS-Sequences-r16 [15] INTEGER (1..2),
   msgA-Alpha-r16 [16] ENUMERATED { alpha0(0), alpha04(1), alpha05(2), 
      alpha06(3), alpha07(4), alpha08(5), alpha09(6), alpha1(7) } OPTIONAL, -- Need S
   interlaceIndexFirstPO-MsgA-PUSCH-r16 [17] INTEGER (1..10) OPTIONAL, -- Need R
   nrofInterlacesPerMsgA-PO-r16 [18] INTEGER (1..10) OPTIONAL,
   ...
}

-- TAG-MSGACONFIGCOMMON-STOP
-- TAG-MSGA-PUSCH-CONFIG-START
MsgA-PUSCH-Config-r16 ::= SEQUENCE {
   msgA-PUSCH-ResourceGroupA-r16 [0] MsgA-PUSCH-Resource-r16 OPTIONAL, -- Cond InitialBWPConfig
   msgA-PUSCH-ResourceGroupB-r16 [1] MsgA-PUSCH-Resource-r16 OPTIONAL, -- Cond GroupBConfigured
   msgA-TransformPrecoder-r16 [2] ENUMERATED { enabled(0), disabled(1) }
       OPTIONAL, -- Need R
   msgA-DataScramblingIndex-r16 [3] INTEGER (0..1023) OPTIONAL, -- Need S
   msgA-DeltaPreamble-r16 [4] INTEGER (-1..6) OPTIONAL -- Need R
}

-- TAG-FEATURECOMBINATION-STOP
-- TAG-FEATURECOMBINATIONPREAMBLES-START
FeatureCombinationPreambles-r17 ::= SEQUENCE {
   featureCombination-r17 [0] FeatureCombination-r17,
   startPreambleForThisPartition-r17 [1] INTEGER (0..63),
   numberOfPreamblesPerSSB-ForThisPartition-r17 [2] INTEGER (1..64),
   ssb-SharedRO-MaskIndex-r17 [3] INTEGER (1..15) OPTIONAL, -- Need S
   groupBconfigured-r17 [4] SEQUENCE {
      ra-SizeGroupA-r17 [0] ENUMERATED { b56(0), b144(1), b208(2), b256(3), 
         b282(4), b480(5), b640(6), b800(7), b1000(8), b72(9), spare6(10), 
         spare5(11), spare4(12), spare3(13), spare2(14), spare1(15) },
      messagePowerOffsetGroupB-r17 [1] ENUMERATED { minusinfinity(0), dB0(1), 
         dB5(2), dB8(3), dB10(4), dB12(5), dB15(6), dB18(7) },
      numberOfRA-PreamblesGroupA-r17 [2] INTEGER (1..64)
   } OPTIONAL, -- Need R
   separateMsgA-PUSCH-Config-r17 [5] MsgA-PUSCH-Config-r16 OPTIONAL, -- Cond MsgAConfigCommon
   msgA-RSRP-Threshold-r17 [6] RSRP-Range OPTIONAL, -- Need R
   rsrp-ThresholdSSB-r17 [7] RSRP-Range OPTIONAL, -- Need R
   deltaPreamble-r17 [8] INTEGER (-1..6) OPTIONAL,
   ...
}

-- TAG-QUANTITYCONFIG-STOP
-- TAG-RACH-CONFIGCOMMON-START
RACH-ConfigCommon ::= SEQUENCE {
   rach-ConfigGeneric [0] RACH-ConfigGeneric,
   totalNumberOfRA-Preambles [1] INTEGER (1..63) OPTIONAL, -- Need S
   ssb-perRACH-OccasionAndCB-PreamblesPerSSB [2] EXPLICIT CHOICE {
      oneEighth [0] ENUMERATED { n4(0), n8(1), n12(2), n16(3), n20(4), n24(5), 
         n28(6), n32(7), n36(8), n40(9), n44(10), n48(11), n52(12), n56(13), 
         n60(14), n64(15) },
      oneFourth [1] ENUMERATED { n4(0), n8(1), n12(2), n16(3), n20(4), n24(5), 
         n28(6), n32(7), n36(8), n40(9), n44(10), n48(11), n52(12), n56(13), 
         n60(14), n64(15) },
      oneHalf [2] ENUMERATED { n4(0), n8(1), n12(2), n16(3), n20(4), n24(5), 
         n28(6), n32(7), n36(8), n40(9), n44(10), n48(11), n52(12), n56(13), 
         n60(14), n64(15) },
      one [3] ENUMERATED { n4(0), n8(1), n12(2), n16(3), n20(4), n24(5), n28(6)
         , n32(7), n36(8), n40(9), n44(10), n48(11), n52(12), n56(13), n60(14)
         , n64(15) },
      two [4] ENUMERATED { n4(0), n8(1), n12(2), n16(3), n20(4), n24(5), n28(6)
         , n32(7) },
      four [5] INTEGER (1..16),
      eight [6] INTEGER (1..8),
      sixteen [7] INTEGER (1..4)
   } OPTIONAL, -- Need M
   groupBconfigured [3] SEQUENCE {
      ra-Msg3SizeGroupA [0] ENUMERATED { b56(0), b144(1), b208(2), b256(3), 
         b282(4), b480(5), b640(6), b800(7), b1000(8), b72(9), spare6(10), 
         spare5(11), spare4(12), spare3(13), spare2(14), spare1(15) },
      messagePowerOffsetGroupB [1] ENUMERATED { minusinfinity(0), dB0(1), 
         dB5(2), dB8(3), dB10(4), dB12(5), dB15(6), dB18(7) },
      numberOfRA-PreamblesGroupA [2] INTEGER (1..64)
   } OPTIONAL, -- Need R
   ra-ContentionResolutionTimer [4] ENUMERATED { sf8(0), sf16(1), sf24(2), 
      sf32(3), sf40(4), sf48(5), sf56(6), sf64(7) },
   rsrp-ThresholdSSB [5] RSRP-Range OPTIONAL, -- Need R
   rsrp-ThresholdSSB-SUL [6] RSRP-Range OPTIONAL, -- Cond SUL
   prach-RootSequenceIndex [7] EXPLICIT CHOICE {
      l839 [0] INTEGER (0..837),
      l139 [1] INTEGER (0..137)
   },
   msg1-SubcarrierSpacing [8] SubcarrierSpacing OPTIONAL, -- Cond L139
   restrictedSetConfig [9] ENUMERATED { unrestrictedSet(0), 
      restrictedSetTypeA(1), restrictedSetTypeB(2) },
   msg3-transformPrecoder [10] ENUMERATED { enabled(0) } OPTIONAL,
   ...,
   [[
      ra-PrioritizationForAccessIdentity-r16 [11] SEQUENCE {
         ra-Prioritization-r16 [0] RA-Prioritization,
         ra-PrioritizationForAI-r16 [1] BIT STRING  (SIZE (2))
      } OPTIONAL,
      prach-RootSequenceIndex-r16 [12] EXPLICIT CHOICE {
         l571 [0] INTEGER (0..569),
         l1151 [1] INTEGER (0..1149)
      } OPTIONAL
   ]],
   [[
      ra-PrioritizationForSlicing-r17 [13] RA-PrioritizationForSlicing-r17
          OPTIONAL,
      featureCombinationPreamblesList-r17 [14] SEQUENCE (SIZE (1..maxFeatureCombPreamblesPerRACHResource-r17)) OF 
         FeatureCombinationPreambles-r17 OPTIONAL
   ]]
}

-- TAG-PUSCH-CONFIG-STOP
-- TAG-PUSCH-CONFIGCOMMON-START
PUSCH-ConfigCommon ::= SEQUENCE {
   groupHoppingEnabledTransformPrecoding [0] ENUMERATED { enabled(0) } OPTIONAL
      , -- Need R
   pusch-TimeDomainAllocationList [1] PUSCH-TimeDomainResourceAllocationList
       OPTIONAL, -- Need R
   msg3-DeltaPreamble [2] INTEGER (-1..6) OPTIONAL, -- Need R
   p0-NominalWithGrant [3] INTEGER (-202..24) OPTIONAL,
   ...
}

-- TAG-PUCCH-CONFIG-STOP
-- TAG-PUCCH-CONFIGCOMMON-START
PUCCH-ConfigCommon ::= SEQUENCE {
   pucch-ResourceCommon [0] INTEGER (0..15) OPTIONAL, -- Cond InitialBWP-Only
   pucch-GroupHopping [1] ENUMERATED { neither(0), enable(1), disable(2) },
   hoppingId [2] INTEGER (0..1023) OPTIONAL, -- Need R
   p0-nominal [3] INTEGER (-202..24) OPTIONAL,
   ...,
   [[
      nrofPRBs [4] INTEGER (1..16) OPTIONAL,
      intra-SlotFH-r17 [5] ENUMERATED { fromLowerEdge(0), fromUpperEdge(1) }
          OPTIONAL,
      pucch-ResourceCommonRedCap-r17 [6] INTEGER (0..15) OPTIONAL,
      additionalPRBOffset-r17 [7] ENUMERATED { n2(0), n3(1), n4(2), n6(3), 
         n8(4), n9(5), n10(6), n12(7) } OPTIONAL
   ]]
}

-- TAG-RACH-CONFIGGENERIC-STOP
-- TAG-RACH-CONFIGGENERICTWOSTEPRA-START
RACH-ConfigGenericTwoStepRA-r16 ::= SEQUENCE {
   msgA-PRACH-ConfigurationIndex-r16 [0] INTEGER (0..262) OPTIONAL, -- Cond 2StepOnly
   msgA-RO-FDM-r16 [1] ENUMERATED { one(0), two(1), four(2), eight(3) }
       OPTIONAL, -- Cond 2StepOnly
   msgA-RO-FrequencyStart-r16 [2] INTEGER (0..maxNrofPhysicalResourceBlocks-1) OPTIONAL, -- Cond 2StepOnly
   msgA-ZeroCorrelationZoneConfig-r16 [3] INTEGER (0..15) OPTIONAL, -- Cond 2StepOnly
   msgA-PreamblePowerRampingStep-r16 [4] ENUMERATED { dB0(0), dB2(1), dB4(2), 
      dB6(3) } OPTIONAL, -- Cond 2StepOnlyNoCFRA
   msgA-PreambleReceivedTargetPower-r16 [5] INTEGER (-202..-60) OPTIONAL, -- Cond 2StepOnlyNoCFRA
   msgB-ResponseWindow-r16 [6] ENUMERATED { sl1(0), sl2(1), sl4(2), sl8(3), 
      sl10(4), sl20(5), sl40(6), sl80(7), sl160(8), sl320(9) } OPTIONAL,
                                                                                                                       -- Cond NoCFRA
   preambleTransMax-r16 [7] ENUMERATED { n3(0), n4(1), n5(2), n6(3), n7(4), 
      n8(5), n10(6), n20(7), n50(8), n100(9), n200(10) } OPTIONAL,
   ...,
   [[
      msgB-ResponseWindow-v1700 [8] ENUMERATED { sl240(0), sl640(1), sl960(2), 
         sl1280(3), sl1920(4), sl2560(5) } OPTIONAL
   ]]
}

GroupB-ConfiguredTwoStepRA-r16 ::= SEQUENCE {
   ra-MsgA-SizeGroupA-r16 [0] ENUMERATED { b56(0), b144(1), b208(2), b256(3), 
      b282(4), b480(5), b640(6), b800(7), b1000(8), b72(9), spare6(10), 
      spare5(11), spare4(12), spare3(13), spare2(14), spare1(15) },
   messagePowerOffsetGroupB-r16 [1] ENUMERATED { minusinfinity(0), dB0(1), 
      dB5(2), dB8(3), dB10(4), dB12(5), dB15(6), dB18(7) },
   numberOfRA-PreamblesGroupA-r16 [2] INTEGER (1..64)
}

-- TAG-RACH-CONFIGCOMMON-STOP
-- TAG-RACH-CONFIGCOMMONTWOSTEPRA-START
RACH-ConfigCommonTwoStepRA-r16 ::= SEQUENCE {
   rach-ConfigGenericTwoStepRA-r16 [0] RACH-ConfigGenericTwoStepRA-r16,
   msgA-TotalNumberOfRA-Preambles-r16 [1] INTEGER (1..63) OPTIONAL, -- Need S
   msgA-SSB-PerRACH-OccasionAndCB-PreamblesPerSSB-r16 [2] EXPLICIT CHOICE {
      oneEighth [0] ENUMERATED { n4(0), n8(1), n12(2), n16(3), n20(4), n24(5), 
         n28(6), n32(7), n36(8), n40(9), n44(10), n48(11), n52(12), n56(13), 
         n60(14), n64(15) },
      oneFourth [1] ENUMERATED { n4(0), n8(1), n12(2), n16(3), n20(4), n24(5), 
         n28(6), n32(7), n36(8), n40(9), n44(10), n48(11), n52(12), n56(13), 
         n60(14), n64(15) },
      oneHalf [2] ENUMERATED { n4(0), n8(1), n12(2), n16(3), n20(4), n24(5), 
         n28(6), n32(7), n36(8), n40(9), n44(10), n48(11), n52(12), n56(13), 
         n60(14), n64(15) },
      one [3] ENUMERATED { n4(0), n8(1), n12(2), n16(3), n20(4), n24(5), n28(6)
         , n32(7), n36(8), n40(9), n44(10), n48(11), n52(12), n56(13), n60(14)
         , n64(15) },
      two [4] ENUMERATED { n4(0), n8(1), n12(2), n16(3), n20(4), n24(5), n28(6)
         , n32(7) },
      four [5] INTEGER (1..16),
      eight [6] INTEGER (1..8),
      sixteen [7] INTEGER (1..4)
   } OPTIONAL, -- Cond 2StepOnly
   msgA-CB-PreamblesPerSSB-PerSharedRO-r16 [3] INTEGER (1..60) OPTIONAL, -- Cond SharedRO
   msgA-SSB-SharedRO-MaskIndex-r16 [4] INTEGER (1..15) OPTIONAL, -- Need S
   groupB-ConfiguredTwoStepRA-r16 [5] GroupB-ConfiguredTwoStepRA-r16 OPTIONAL, -- Need S
   msgA-PRACH-RootSequenceIndex-r16 [6] EXPLICIT CHOICE {
      l839 [0] INTEGER (0..837),
      l139 [1] INTEGER (0..137),
      l571 [2] INTEGER (0..569),
      l1151 [3] INTEGER (0..1149)
   } OPTIONAL, -- Cond 2StepOnly
   msgA-TransMax-r16 [7] ENUMERATED { n1(0), n2(1), n4(2), n6(3), n8(4), n10(5)
      , n20(6), n50(7), n100(8), n200(9) } OPTIONAL, -- Need R
   msgA-RSRP-Threshold-r16 [8] RSRP-Range OPTIONAL, -- Cond 2Step4Step
   msgA-RSRP-ThresholdSSB-r16 [9] RSRP-Range OPTIONAL, -- Need R
   msgA-SubcarrierSpacing-r16 [10] SubcarrierSpacing OPTIONAL, -- Cond 2StepOnlyL139
   msgA-RestrictedSetConfig-r16 [11] ENUMERATED { unrestrictedSet(0), 
      restrictedSetTypeA(1), restrictedSetTypeB(2) } OPTIONAL, -- Cond 2StepOnly
   ra-PrioritizationForAccessIdentityTwoStep-r16 [12] SEQUENCE {
      ra-Prioritization-r16 [0] RA-Prioritization,
      ra-PrioritizationForAI-r16 [1] BIT STRING  (SIZE (2))
   } OPTIONAL, -- Cond InitialBWP-Only
   ra-ContentionResolutionTimer-r16 [13] ENUMERATED { sf8(0), sf16(1), sf24(2)
      , sf32(3), sf40(4), sf48(5), sf56(6), sf64(7) } OPTIONAL,
   ...,
   [[
      ra-PrioritizationForSlicingTwoStep-r17 [14] 
         RA-PrioritizationForSlicing-r17 OPTIONAL,
      featureCombinationPreamblesList-r17 [15] SEQUENCE (SIZE (1..maxFeatureCombPreamblesPerRACHResource-r17)) OF 
         FeatureCombinationPreambles-r17 OPTIONAL
   ]]
}

-- TAG-MRB-IDENTITY-STOP
-- TAG-MSGACONFIGCOMMON-START
MsgA-ConfigCommon-r16 ::= SEQUENCE {
   rach-ConfigCommonTwoStepRA-r16 [0] RACH-ConfigCommonTwoStepRA-r16,
   msgA-PUSCH-Config-r16 [1] MsgA-PUSCH-Config-r16 OPTIONAL --Cond InitialBWPConfig
}

AdditionalRACH-Config-r17 ::= SEQUENCE {
   rach-ConfigCommon-r17 [0] RACH-ConfigCommon OPTIONAL, -- Need R
   msgA-ConfigCommon-r17 [1] MsgA-ConfigCommon-r16 OPTIONAL,
   ...
}

AdditionalRACH-ConfigList-r17 ::= SEQUENCE (SIZE (1..maxAdditionalRACH-r17)) OF 
   AdditionalRACH-Config-r17

-- TAG-BWP-UPLINK-STOP
-- TAG-BWP-UPLINKCOMMON-START
BWP-UplinkCommon ::= SEQUENCE {
   genericParameters [0] BWP,
   rach-ConfigCommon [1] EXPLICIT CHOICE {
      release [0] NULL,
      setup [1] EXPLICIT RACH-ConfigCommon
   } OPTIONAL, -- Need M
   pusch-ConfigCommon [2] EXPLICIT CHOICE {
      release [0] NULL,
      setup [1] EXPLICIT PUSCH-ConfigCommon
   } OPTIONAL, -- Need M
   pucch-ConfigCommon [3] EXPLICIT CHOICE {
      release [0] NULL,
      setup [1] EXPLICIT PUCCH-ConfigCommon
   } OPTIONAL,
   ...,
   [[
      rach-ConfigCommonIAB-r16 [4] EXPLICIT CHOICE {
         release [0] NULL,
         setup [1] EXPLICIT RACH-ConfigCommon
      } OPTIONAL,
      useInterlacePUCCH-PUSCH-r16 [5] ENUMERATED { enabled(0) } OPTIONAL,
      msgA-ConfigCommon-r16 [6] EXPLICIT CHOICE {
         release [0] NULL,
         setup [1] EXPLICIT MsgA-ConfigCommon-r16
      } OPTIONAL
   ]],
   [[
      enableRA-PrioritizationForSlicing-r17 [7] BOOLEAN OPTIONAL,
      additionalRACH-ConfigList-r17 [8] EXPLICIT CHOICE {
         release [0] NULL,
         setup [1] EXPLICIT AdditionalRACH-ConfigList-r17
      } OPTIONAL,
      rsrp-ThresholdMsg3-r17 [9] RSRP-Range OPTIONAL,
      numberOfMsg3-RepetitionsList-r17 [10] SEQUENCE (SIZE (4)) OF 
         NumberOfMsg3-Repetitions-r17 OPTIONAL,
      mcs-Msg3-Repetitions-r17 [11] SEQUENCE (SIZE (8)) OF INTEGER (0..31) OPTIONAL
   ]]
}

-- TAG-UPLINKCONFIGCOMMON-STOP
-- TAG-UPLINKCONFIGCOMMONSIB-START
UplinkConfigCommonSIB ::= SEQUENCE {
   frequencyInfoUL [0] FrequencyInfoUL-SIB,
   initialUplinkBWP [1] BWP-UplinkCommon,
   timeAlignmentTimerCommon [2] TimeAlignmentTimer
}

TDD-UL-DL-Pattern ::= SEQUENCE {
   dl-UL-TransmissionPeriodicity [0] ENUMERATED { ms0p5(0), ms0p625(1), ms1(2)
      , ms1p25(3), ms2(4), ms2p5(5), ms5(6), ms10(7) },
   nrofDownlinkSlots [1] INTEGER (0..maxNrofSlots),
   nrofDownlinkSymbols [2] INTEGER (0..maxNrofSymbols-1),
   nrofUplinkSlots [3] INTEGER (0..maxNrofSlots),
   nrofUplinkSymbols [4] INTEGER (0..maxNrofSymbols-1),
   ...,
   [[
      dl-UL-TransmissionPeriodicity-v1530 [5] ENUMERATED { ms3(0), ms4(1) }
          OPTIONAL
   ]]
}

-- TAG-TCI-UL-STATEID-STOP
-- TAG-TDD-UL-DL-CONFIGCOMMON-START
TDD-UL-DL-ConfigCommon ::= SEQUENCE {
   referenceSubcarrierSpacing [0] SubcarrierSpacing,
   pattern1 [1] TDD-UL-DL-Pattern,
   pattern2 [2] TDD-UL-DL-Pattern OPTIONAL,
   ...
}

-- TAG-SECURITYALGORITHMCONFIG-STOP
-- TAG-SEMISTATICCHANNELACCESSCONFIG-START
SemiStaticChannelAccessConfig-r16 ::= SEQUENCE {
   period-r16 [0] ENUMERATED { ms1(0), ms2(1), ms2dot5(2), ms4(3), ms5(4), 
      ms10(5) }
}

-- TAG-GAPPRIORITY-STOP
-- TAG-HIGHSPEEDCONFIG-START
HighSpeedConfig-r16 ::= SEQUENCE {
   highSpeedMeasFlag-r16 [0] ENUMERATED { true(0) } OPTIONAL, -- Cond SpCellOnly
   highSpeedDemodFlag-r16 [1] ENUMERATED { true(0) } OPTIONAL,
   ...
}

HighSpeedConfigFR2-r17 ::= SEQUENCE {
   highSpeedMeasFlagFR2-r17 [0] ENUMERATED { set1(0), set2(1) } OPTIONAL, -- Need R
   highSpeedDeploymentTypeFR2-r17 [1] ENUMERATED { unidirectional(0), 
      bidirectional(1) } OPTIONAL, -- Need R
   highSpeedLargeOneStepUL-TimingFR2-r17 [2] ENUMERATED { true(0) } OPTIONAL,
   ...
}

UplinkConfigCommonSIB-v1700 ::= SEQUENCE {
   initialUplinkBWP-RedCap-r17 [0] BWP-UplinkCommon OPTIONAL -- Need R
}

FrequencyInfoDL-SIB-v1760 ::= SEQUENCE {
   frequencyBandList-v1760 [0] MultiFrequencyBandListNR-SIB-v1760
}

DownlinkConfigCommonSIB-v1760 ::= SEQUENCE {
   frequencyInfoDL-v1760 [0] FrequencyInfoDL-SIB-v1760
}

FrequencyInfoUL-SIB-v1760 ::= SEQUENCE {
   frequencyBandList-v1760 [0] MultiFrequencyBandListNR-SIB-v1760
}

UplinkConfigCommonSIB-v1760 ::= SEQUENCE {
   frequencyInfoUL-v1760 [0] FrequencyInfoUL-SIB-v1760
}

-- TAG-SERVINGCELLCONFIGCOMMON-STOP
-- TAG-SERVINGCELLCONFIGCOMMONSIB-START
ServingCellConfigCommonSIB ::= SEQUENCE {
   downlinkConfigCommon [0] DownlinkConfigCommonSIB,
   uplinkConfigCommon [1] UplinkConfigCommonSIB OPTIONAL, -- Need R
   supplementaryUplink [2] UplinkConfigCommonSIB OPTIONAL, -- Need R
   n-TimingAdvanceOffset [3] ENUMERATED { n0(0), n25600(1), n39936(2) }
       OPTIONAL, -- Need S
   ssb-PositionsInBurst [4] SEQUENCE {
      inOneGroup [0] BIT STRING  (SIZE (8)),
      groupPresence [1] BIT STRING  (SIZE (8)) OPTIONAL -- Cond FR2-Only
   },
   ssb-PeriodicityServingCell [5] ENUMERATED { ms5(0), ms10(1), ms20(2), 
      ms40(3), ms80(4), ms160(5) },
   tdd-UL-DL-ConfigurationCommon [6] TDD-UL-DL-ConfigCommon OPTIONAL, -- Cond TDD
   ss-PBCH-BlockPower [7] INTEGER (-60..50),
   ...,
   [[
      channelAccessMode-r16 [8] EXPLICIT CHOICE {
         dynamic [0] NULL,
         semiStatic [1] SemiStaticChannelAccessConfig-r16
      } OPTIONAL,
      discoveryBurstWindowLength-r16 [9] ENUMERATED { ms0dot5(0), ms1(1), 
         ms2(2), ms3(3), ms4(4), ms5(5) } OPTIONAL,
      highSpeedConfig-r16 [10] HighSpeedConfig-r16 OPTIONAL
   ]],
   [[
      channelAccessMode2-r17 [11] ENUMERATED { enabled(0) } OPTIONAL,
      discoveryBurstWindowLength-v1700 [12] ENUMERATED { ms0dot125(0), 
         ms0dot25(1), ms0dot5(2), ms0dot75(3), ms1(4), ms1dot25(5) } OPTIONAL,
      highSpeedConfigFR2-r17 [13] HighSpeedConfigFR2-r17 OPTIONAL,
      uplinkConfigCommon-v1700 [14] UplinkConfigCommonSIB-v1700 OPTIONAL
   ]],
   [[
      enhancedMeasurementLEO-r17 [15] ENUMERATED { true(0) } OPTIONAL
   ]],
   [[
      ra-ChannelAccess-r17 [16] ENUMERATED { enabled(0) } OPTIONAL
   ]],
   [[
      downlinkConfigCommon-v1760 [17] DownlinkConfigCommonSIB-v1760 OPTIONAL,
      uplinkConfigCommon-v1760 [18] UplinkConfigCommonSIB-v1760 OPTIONAL
   ]]
}

-- TAG-UAC-BARRINGPERPLMN-LIST-STOP
-- TAG-UE-TIMERSANDCONSTANTS-START
UE-TimersAndConstants ::= SEQUENCE {
   t300 [0] ENUMERATED { ms100(0), ms200(1), ms300(2), ms400(3), ms600(4), 
      ms1000(5), ms1500(6), ms2000(7) },
   t301 [1] ENUMERATED { ms100(0), ms200(1), ms300(2), ms400(3), ms600(4), 
      ms1000(5), ms1500(6), ms2000(7) },
   t310 [2] ENUMERATED { ms0(0), ms50(1), ms100(2), ms200(3), ms500(4), 
      ms1000(5), ms2000(6) },
   n310 [3] ENUMERATED { n1(0), n2(1), n3(2), n4(3), n6(4), n8(5), n10(6), 
      n20(7) },
   t311 [4] ENUMERATED { ms1000(0), ms3000(1), ms5000(2), ms10000(3), 
      ms15000(4), ms20000(5), ms30000(6) },
   n311 [5] ENUMERATED { n1(0), n2(1), n3(2), n4(3), n5(4), n6(5), n8(6), 
      n10(7) },
   t319 [6] ENUMERATED { ms100(0), ms200(1), ms300(2), ms400(3), ms600(4), 
      ms1000(5), ms1500(6), ms2000(7) },
   ...
}

UAC-BarringPerCat ::= SEQUENCE {
   accessCategory [0] INTEGER (1..maxAccessCat-1),
   uac-barringInfoSetIndex [1] UAC-BarringInfoSetIndex
}

-- TAG-UAC-BARRINGINFOSETLIST-STOP
-- TAG-UAC-BARRINGPERCATLIST-START
UAC-BarringPerCatList ::= SEQUENCE (SIZE (1..maxAccessCat-1)) OF UAC-BarringPerCat

UAC-BarringPerPLMN ::= SEQUENCE {
   plmn-IdentityIndex [0] INTEGER (1..maxPLMN),
   uac-ACBarringListType [1] EXPLICIT CHOICE {
      uac-ImplicitACBarringList [0] SEQUENCE (SIZE (maxAccessCat-1)) OF 
         UAC-BarringInfoSetIndex,
      uac-ExplicitACBarringList [1] UAC-BarringPerCatList
   } OPTIONAL -- Need S
}

-- TAG-UAC-BARRINGPERCATLIST-STOP
-- TAG-UAC-BARRINGPERPLMN-LIST-START
UAC-BarringPerPLMN-List ::= SEQUENCE (SIZE (1..maxPLMN)) OF UAC-BarringPerPLMN

UAC-BarringInfoSet ::= SEQUENCE {
   uac-BarringFactor [0] ENUMERATED { p00(0), p05(1), p10(2), p15(3), p20(4), 
      p25(5), p30(6), p40(7), p50(8), p60(9), p70(10), p75(11), p80(12), 
      p85(13), p90(14), p95(15) },
   uac-BarringTime [1] ENUMERATED { s4(0), s8(1), s16(2), s32(3), s64(4), 
      s128(5), s256(6), s512(7) },
   uac-BarringForAccessIdentity [2] BIT STRING  (SIZE (7))
}

-- TAG-UAC-BARRINGINFOSETINDEX-STOP
-- TAG-UAC-BARRINGINFOSETLIST-START
UAC-BarringInfoSetList ::= SEQUENCE (SIZE (1..maxBarringInfoSet)) OF UAC-BarringInfoSet

GNSS-ID-r16 ::= SEQUENCE {
   gnss-id-r16 [0] ENUMERATED { gps(0), sbas(1), qzss(2), galileo(3), 
      glonass(4), bds(5), ..., navic-v1760(6) },
   ...
}

SBAS-ID-r16 ::= SEQUENCE {
   sbas-id-r16 [0] ENUMERATED { waas(0), egnos(1), msas(2), gagan(3), ... },
   ...
}

PosSIB-Type-r16 ::= SEQUENCE {
   encrypted-r16 [0] ENUMERATED { true(0) } OPTIONAL, -- Need R
   gnss-id-r16 [1] GNSS-ID-r16 OPTIONAL, -- Need R
   sbas-id-r16 [2] SBAS-ID-r16 OPTIONAL, -- Cond GNSS-ID-SBAS
   posSibType-r16 [3] ENUMERATED { posSibType1-1(0), posSibType1-2(1), 
      posSibType1-3(2), posSibType1-4(3), posSibType1-5(4), posSibType1-6(5), 
      posSibType1-7(6), posSibType1-8(7), posSibType2-1(8), posSibType2-2(9), 
      posSibType2-3(10), posSibType2-4(11), posSibType2-5(12), 
      posSibType2-6(13), posSibType2-7(14), posSibType2-8(15), 
      posSibType2-9(16), posSibType2-10(17), posSibType2-11(18), 
      posSibType2-12(19), posSibType2-13(20), posSibType2-14(21), 
      posSibType2-15(22), posSibType2-16(23), posSibType2-17(24), 
      posSibType2-18(25), posSibType2-19(26), posSibType2-20(27), 
      posSibType2-21(28), posSibType2-22(29), posSibType2-23(30), 
      posSibType3-1(31), posSibType4-1(32), posSibType5-1(33), 
      posSibType6-1(34), posSibType6-2(35), posSibType6-3(36), ... },
   areaScope-r16 [4] ENUMERATED { true(0) } OPTIONAL -- Need S
}

PosSIB-MappingInfo-r16 ::= SEQUENCE (SIZE (1..maxSIB)) OF PosSIB-Type-r16

PosSchedulingInfo-r16 ::= SEQUENCE {
   offsetToSI-Used-r16 [0] ENUMERATED { true(0) } OPTIONAL, -- Need R
   posSI-Periodicity-r16 [1] ENUMERATED { rf8(0), rf16(1), rf32(2), rf64(3), 
      rf128(4), rf256(5), rf512(6) },
   posSI-BroadcastStatus-r16 [2] ENUMERATED { broadcasting(0), 
      notBroadcasting(1) },
   posSIB-MappingInfo-r16 [3] PosSIB-MappingInfo-r16,
   ...
}

-- TAG-POSSYSTEMINFORMATION-R16-IES-STOP
-- TAG-POSSI-SCHEDULINGINFO-START
PosSI-SchedulingInfo-r16 ::= SEQUENCE {
   posSchedulingInfoList-r16 [0] SEQUENCE (SIZE (1..maxSI-Message)) OF PosSchedulingInfo-r16,
   posSI-RequestConfig-r16 [1] SI-RequestConfig OPTIONAL, -- Cond MSG-1
   posSI-RequestConfigSUL-r16 [2] SI-RequestConfig OPTIONAL,
   ...,
   [[
      posSI-RequestConfigRedCap-r17 [3] SI-RequestConfig OPTIONAL
   ]]
}

UAC-BarringInfoSet-v1700 ::= SEQUENCE {
   uac-BarringFactorForAI3-r17 [0] ENUMERATED { p00(0), p05(1), p10(2), p15(3)
      , p20(4), p25(5), p30(6), p40(7), p50(8), p60(9), p70(10), p75(11), 
      p80(12), p85(13), p90(14), p95(15) } OPTIONAL
                                                                                  -- Need S
}

UAC-BarringInfoSetList-v1700 ::= SEQUENCE (SIZE (1..maxBarringInfoSet)) OF 
   UAC-BarringInfoSet-v1700

SDT-ConfigCommonSIB-r17 ::= SEQUENCE {
   sdt-RSRP-Threshold-r17 [0] RSRP-Range OPTIONAL, -- Need R
   sdt-LogicalChannelSR-DelayTimer-r17 [1] ENUMERATED { sf20(0), sf40(1), 
      sf64(2), sf128(3), sf512(4), sf1024(5), sf2560(6), spare1(7) } OPTIONAL, -- Need R
   sdt-DataVolumeThreshold-r17 [2] ENUMERATED { byte32(0), byte100(1), 
      byte200(2), byte400(3), byte600(4), byte800(5), byte1000(6), byte2000(7)
      , byte4000(8), byte8000(9), byte9000(10), byte10000(11), byte12000(12), 
      byte24000(13), byte48000(14), byte96000(15) },
   t319a-r17 [3] ENUMERATED { ms100(0), ms200(1), ms300(2), ms400(3), ms600(4)
      , ms1000(5), ms2000(6), ms3000(7), ms4000(8), spare7(9), spare6(10), 
      spare5(11), spare4(12), spare3(13), spare2(14), spare1(15) }
}

RedCap-ConfigCommonSIB-r17 ::= SEQUENCE {
   halfDuplexRedCapAllowed-r17 [0] ENUMERATED { true(0) } OPTIONAL, -- Need R
   cellBarredRedCap-r17 [1] SEQUENCE {
      cellBarredRedCap1Rx-r17 [0] ENUMERATED { barred(0), notBarred(1) },
      cellBarredRedCap2Rx-r17 [1] ENUMERATED { barred(0), notBarred(1) }
   } OPTIONAL,
   ...
}

SIB-TypeInfo-v1700 ::= SEQUENCE {
   sibType-r17 [0] EXPLICIT CHOICE {
      type1-r17 [0] ENUMERATED { sibType15(0), sibType16(1), sibType17(2), 
         sibType18(3), sibType19(4), sibType20(5), sibType21(6), spare9(7), 
         spare8(8), spare7(9), spare6(10), spare5(11), spare4(12), spare3(13), 
         spare2(14), spare1(15), ... },
      type2-r17 [1] SEQUENCE {
         posSibType-r17 [0] ENUMERATED { posSibType1-9(0), posSibType1-10(1), 
            posSibType2-24(2), posSibType2-25(3), posSibType6-4(4), 
            posSibType6-5(5), posSibType6-6(6), posSibType2-17a-v1770(7), 
            posSibType2-18a-v1770(8), posSibType2-20a-v1770(9), spare6(10), 
            spare5(11), spare4(12), spare3(13), spare2(14), spare1(15), ... },
         encrypted-r17 [1] ENUMERATED { true(0) } OPTIONAL, -- Need R
         gnss-id-r17 [2] GNSS-ID-r16 OPTIONAL, -- Need R
         sbas-id-r17 [3] SBAS-ID-r16 OPTIONAL -- Cond GNSS-ID-SBAS
      }
   },
   valueTag-r17 [1] INTEGER (0..31) OPTIONAL, -- Cond NonPosSIB
   areaScope-r17 [2] ENUMERATED { true(0) } OPTIONAL -- Need S
}

SIB-Mapping-v1700 ::= SEQUENCE (SIZE (1..maxSIB)) OF SIB-TypeInfo-v1700

SchedulingInfo2-r17 ::= SEQUENCE {
   si-BroadcastStatus-r17 [0] ENUMERATED { broadcasting(0), notBroadcasting(1)
       },
   si-WindowPosition-r17 [1] INTEGER (1..256),
   si-Periodicity-r17 [2] ENUMERATED { rf8(0), rf16(1), rf32(2), rf64(3), 
      rf128(4), rf256(5), rf512(6) },
   sib-MappingInfo-r17 [3] SIB-Mapping-v1700
}

SI-SchedulingInfo-v1700 ::= SEQUENCE {
   schedulingInfoList2-r17 [0] SEQUENCE (SIZE (1..maxSI-Message)) OF SchedulingInfo2-r17,
   dummy [1] SI-RequestConfig OPTIONAL
}

SI-SchedulingInfo-v1740 ::= SEQUENCE {
   si-RequestConfigRedCap-r17 [0] SI-RequestConfig OPTIONAL -- Cond REDCAP-MSG-1
}

SIB1-v1740-IEs ::= SEQUENCE {
   si-SchedulingInfo-v1740 [0] SI-SchedulingInfo-v1740 OPTIONAL, -- Need R
   nonCriticalExtension [1] SEQUENCE {

   } OPTIONAL
}

SIB1-v1700-IEs ::= SEQUENCE {
   hsdn-Cell-r17 [0] ENUMERATED { true(0) } OPTIONAL, -- Need R
   uac-BarringInfo-v1700 [1] SEQUENCE {
      uac-BarringInfoSetList-v1700 [0] UAC-BarringInfoSetList-v1700
   } OPTIONAL, -- Cond MINT
   sdt-ConfigCommon-r17 [2] SDT-ConfigCommonSIB-r17 OPTIONAL, -- Need R
   redCap-ConfigCommon-r17 [3] RedCap-ConfigCommonSIB-r17 OPTIONAL, -- Need R
   featurePriorities-r17 [4] SEQUENCE {
      redCapPriority-r17 [0] FeaturePriority-r17 OPTIONAL, -- Need R
      slicingPriority-r17 [1] FeaturePriority-r17 OPTIONAL, -- Need R
      msg3-Repetitions-Priority-r17 [2] FeaturePriority-r17 OPTIONAL, -- Need R
      sdt-Priority-r17 [3] FeaturePriority-r17 OPTIONAL -- Need R
   } OPTIONAL, -- Need R
   si-SchedulingInfo-v1700 [5] SI-SchedulingInfo-v1700 OPTIONAL, -- Need R
   hyperSFN-r17 [6] BIT STRING  (SIZE (10)) OPTIONAL, -- Need R
   eDRX-AllowedIdle-r17 [7] ENUMERATED { true(0) } OPTIONAL, -- Need R
   eDRX-AllowedInactive-r17 [8] ENUMERATED { true(0) } OPTIONAL, -- Cond EDRX-RC
   intraFreqReselectionRedCap-r17 [9] ENUMERATED { allowed(0), notAllowed(1) }
       OPTIONAL, -- Need S
   cellBarredNTN-r17 [10] ENUMERATED { barred(0), notBarred(1) } OPTIONAL, -- Need S
   nonCriticalExtension [11] SIB1-v1740-IEs OPTIONAL
}

SIB1-v1630-IEs ::= SEQUENCE {
   uac-BarringInfo-v1630 [0] SEQUENCE {
      uac-AC1-SelectAssistInfo-r16 [0] SEQUENCE (SIZE (2..maxPLMN)) OF 
         UAC-AC1-SelectAssistInfo-r16
   } OPTIONAL, -- Need R
   nonCriticalExtension [1] SIB1-v1700-IEs OPTIONAL
}

SIB1-v1610-IEs ::= SEQUENCE {
   idleModeMeasurementsEUTRA-r16 [0] ENUMERATED { true(0) } OPTIONAL, -- Need R
   idleModeMeasurementsNR-r16 [1] ENUMERATED { true(0) } OPTIONAL, -- Need R
   posSI-SchedulingInfo-r16 [2] PosSI-SchedulingInfo-r16 OPTIONAL, -- Need R
   nonCriticalExtension [3] SIB1-v1630-IEs OPTIONAL
}

-- TAG-SECURITYMODEFAILURE-STOP
-- TAG-SIB1-START
SIB1 ::= SEQUENCE {
   cellSelectionInfo [0] SEQUENCE {
      q-RxLevMin [0] Q-RxLevMin,
      q-RxLevMinOffset [1] INTEGER (1..8) OPTIONAL, -- Need S
      q-RxLevMinSUL [2] Q-RxLevMin OPTIONAL, -- Need R
      q-QualMin [3] Q-QualMin OPTIONAL, -- Need S
      q-QualMinOffset [4] INTEGER (1..8) OPTIONAL -- Need S
   } OPTIONAL, -- Cond Standalone
   cellAccessRelatedInfo [1] CellAccessRelatedInfo,
   connEstFailureControl [2] ConnEstFailureControl OPTIONAL, -- Need R
   si-SchedulingInfo [3] SI-SchedulingInfo OPTIONAL, -- Need R
   servingCellConfigCommon [4] ServingCellConfigCommonSIB OPTIONAL, -- Need R
   ims-EmergencySupport [5] ENUMERATED { true(0) } OPTIONAL, -- Need R
   eCallOverIMS-Support [6] ENUMERATED { true(0) } OPTIONAL, -- Need R
   ue-TimersAndConstants [7] UE-TimersAndConstants OPTIONAL, -- Need R
   uac-BarringInfo [8] SEQUENCE {
      uac-BarringForCommon [0] UAC-BarringPerCatList OPTIONAL, -- Need S
      uac-BarringPerPLMN-List [1] UAC-BarringPerPLMN-List OPTIONAL, -- Need S
      uac-BarringInfoSetList [2] UAC-BarringInfoSetList,
      uac-AccessCategory1-SelectionAssistanceInfo [3] EXPLICIT CHOICE {
         plmnCommon [0] UAC-AccessCategory1-SelectionAssistanceInfo,
         individualPLMNList [1] SEQUENCE (SIZE (2..maxPLMN)) OF 
            UAC-AccessCategory1-SelectionAssistanceInfo
      } OPTIONAL -- Need S
   } OPTIONAL, -- Need R
   useFullResumeID [9] ENUMERATED { true(0) } OPTIONAL, -- Need R
   lateNonCriticalExtension [10] OCTET STRING OPTIONAL,
   nonCriticalExtension [11] SIB1-v1610-IEs OPTIONAL
}

BCCH-DL-SCH-MessageType ::= CHOICE {
   c1 [0] EXPLICIT CHOICE {
      systemInformation [0] SystemInformation,
      systemInformationBlockType1 [1] SIB1
   },
   messageClassExtension [1] SEQUENCE {

   }
}

-- TAG-BCCH-BCH-MESSAGE-STOP
-- TAG-BCCH-DL-SCH-MESSAGE-START
BCCH-DL-SCH-Message ::= SEQUENCE {
   message [0] EXPLICIT BCCH-DL-SCH-MessageType
}

RRCReject-IEs ::= SEQUENCE {
   waitTime [0] RejectWaitTime OPTIONAL, -- Need N
   lateNonCriticalExtension [1] OCTET STRING OPTIONAL,
   nonCriticalExtension [2] SEQUENCE {

   } OPTIONAL
}

-- TAG-RRCRECONFIGURATIONCOMPLETE-STOP
-- TAG-RRCREJECT-START
RRCReject ::= SEQUENCE {
   criticalExtensions [0] EXPLICIT CHOICE {
      rrcReject [0] RRCReject-IEs,
      criticalExtensionsFuture [1] SEQUENCE {

      }
   }
}

EthernetHeaderCompression-r16 ::= SEQUENCE {
   ehc-Common-r16 [0] SEQUENCE {
      ehc-CID-Length-r16 [0] ENUMERATED { bits7(0), bits15(1) },
      ...
   },
   ehc-Downlink-r16 [1] SEQUENCE {
      drb-ContinueEHC-DL-r16 [0] ENUMERATED { true(0) } OPTIONAL,
      ...
   } OPTIONAL, -- Need M
   ehc-Uplink-r16 [2] SEQUENCE {
      maxCID-EHC-UL-r16 [0] INTEGER (1..32767),
      drb-ContinueEHC-UL-r16 [1] ENUMERATED { true(0) } OPTIONAL,
      ...
   } OPTIONAL -- Need M
}

UplinkDataCompression-r17 ::= CHOICE {
   newSetup [0] SEQUENCE {
      bufferSize-r17 [0] ENUMERATED { kbyte2(0), kbyte4(1), kbyte8(2), 
         spare1(3) },
      dictionary-r17 [1] ENUMERATED { sip-SDP(0), operator(1) } OPTIONAL -- Need N
   },
   drb-ContinueUDC [1] NULL
}

-- TAG-PDCCH-SERVINGCELLCONFIG-STOP
-- TAG-PDCP-CONFIG-START
PDCP-Config ::= SEQUENCE {
   drb [0] SEQUENCE {
      discardTimer [0] ENUMERATED { ms10(0), ms20(1), ms30(2), ms40(3), ms50(4)
         , ms60(5), ms75(6), ms100(7), ms150(8), ms200(9), ms250(10), ms300(11)
         , ms500(12), ms750(13), ms1500(14), infinity(15) } OPTIONAL, -- Cond Setup
      pdcp-SN-SizeUL [1] ENUMERATED { len12bits(0), len18bits(1) } OPTIONAL, -- Cond Setup1
      pdcp-SN-SizeDL [2] ENUMERATED { len12bits(0), len18bits(1) } OPTIONAL, -- Cond Setup2
      headerCompression [3] EXPLICIT CHOICE {
         notUsed [0] NULL,
         rohc [1] SEQUENCE {
            maxCID [0] INTEGER (1..16383) DEFAULT 15,
            profiles [1] SEQUENCE {
               profile0x0001 [0] BOOLEAN,
               profile0x0002 [1] BOOLEAN,
               profile0x0003 [2] BOOLEAN,
               profile0x0004 [3] BOOLEAN,
               profile0x0006 [4] BOOLEAN,
               profile0x0101 [5] BOOLEAN,
               profile0x0102 [6] BOOLEAN,
               profile0x0103 [7] BOOLEAN,
               profile0x0104 [8] BOOLEAN
            },
            drb-ContinueROHC [2] ENUMERATED { true(0) } OPTIONAL -- Need N
         },
         uplinkOnlyROHC [2] SEQUENCE {
            maxCID [0] INTEGER (1..16383) DEFAULT 15,
            profiles [1] SEQUENCE {
               profile0x0006 [0] BOOLEAN
            },
            drb-ContinueROHC [2] ENUMERATED { true(0) } OPTIONAL -- Need N
         },
         ...
      },
      integrityProtection [4] ENUMERATED { enabled(0) } OPTIONAL, -- Cond ConnectedTo5GC1
      statusReportRequired [5] ENUMERATED { true(0) } OPTIONAL, -- Cond Rlc-AM-UM
      outOfOrderDelivery [6] ENUMERATED { true(0) } OPTIONAL -- Need R
   } OPTIONAL, -- Cond DRB
   moreThanOneRLC [1] SEQUENCE {
      primaryPath [0] SEQUENCE {
         cellGroup [0] CellGroupId OPTIONAL, -- Need R
         logicalChannel [1] LogicalChannelIdentity OPTIONAL -- Need R
      },
      ul-DataSplitThreshold [1] UL-DataSplitThreshold OPTIONAL, -- Cond SplitBearer
      pdcp-Duplication [2] BOOLEAN OPTIONAL -- Need R
   } OPTIONAL, -- Cond MoreThanOneRLC
   t-Reordering [2] ENUMERATED { ms0(0), ms1(1), ms2(2), ms4(3), ms5(4), ms8(5)
      , ms10(6), ms15(7), ms20(8), ms30(9), ms40(10), ms50(11), ms60(12), 
      ms80(13), ms100(14), ms120(15), ms140(16), ms160(17), ms180(18), 
      ms200(19), ms220(20), ms240(21), ms260(22), ms280(23), ms300(24), 
      ms500(25), ms750(26), ms1000(27), ms1250(28), ms1500(29), ms1750(30), 
      ms2000(31), ms2250(32), ms2500(33), ms2750(34), ms3000(35), spare28(36), 
      spare27(37), spare26(38), spare25(39), spare24(40), spare23(41), 
      spare22(42), spare21(43), spare20(44), spare19(45), spare18(46), 
      spare17(47), spare16(48), spare15(49), spare14(50), spare13(51), 
      spare12(52), spare11(53), spare10(54), spare09(55), spare08(56), 
      spare07(57), spare06(58), spare05(59), spare04(60), spare03(61), 
      spare02(62), spare01(63) } OPTIONAL,
   ...,
   [[
      cipheringDisabled [3] ENUMERATED { true(0) } OPTIONAL
   ]],
   [[
      discardTimerExt-r16 [4] EXPLICIT CHOICE {
         release [0] NULL,
         setup [1] EXPLICIT DiscardTimerExt-r16
      } OPTIONAL,
      moreThanTwoRLC-DRB-r16 [5] SEQUENCE {
         splitSecondaryPath-r16 [0] LogicalChannelIdentity OPTIONAL, -- Cond SplitBearer2
         duplicationState-r16 [1] SEQUENCE (SIZE (3)) OF BOOLEAN OPTIONAL -- Need S
      } OPTIONAL,
      ethernetHeaderCompression-r16 [6] EXPLICIT CHOICE {
         release [0] NULL,
         setup [1] EXPLICIT EthernetHeaderCompression-r16
      } OPTIONAL
   ]],
   [[
      survivalTimeStateSupport-r17 [7] ENUMERATED { true(0) } OPTIONAL,
      uplinkDataCompression-r17 [8] EXPLICIT CHOICE {
         release [0] NULL,
         setup [1] EXPLICIT UplinkDataCompression-r17
      } OPTIONAL,
      discardTimerExt2-r17 [9] EXPLICIT CHOICE {
         release [0] NULL,
         setup [1] EXPLICIT DiscardTimerExt2-r17
      } OPTIONAL,
      initialRX-DELIV-r17 [10] BIT STRING  (SIZE (32)) OPTIONAL
   ]]
}

SRB-ToAddMod ::= SEQUENCE {
   srb-Identity [0] SRB-Identity,
   reestablishPDCP [1] ENUMERATED { true(0) } OPTIONAL, -- Need N
   discardOnPDCP [2] ENUMERATED { true(0) } OPTIONAL, -- Need N
   pdcp-Config [3] PDCP-Config OPTIONAL,
   ...,
   [[
      srb-Identity-v1700 [4] SRB-Identity-v1700 OPTIONAL
   ]]
}

SRB-ToAddModList ::= SEQUENCE (SIZE (1..2)) OF SRB-ToAddMod

-- TAG-SCS-SPECIFICCARRIER-STOP
-- TAG-SDAP-CONFIG-START
SDAP-Config ::= SEQUENCE {
   pdu-Session [0] PDU-SessionID,
   sdap-HeaderDL [1] ENUMERATED { present(0), absent(1) },
   sdap-HeaderUL [2] ENUMERATED { present(0), absent(1) },
   defaultDRB [3] BOOLEAN,
   mappedQoS-FlowsToAdd [4] SEQUENCE (SIZE (1..maxNrofQFIs)) OF QFI OPTIONAL, -- Need N
   mappedQoS-FlowsToRelease [5] SEQUENCE (SIZE (1..maxNrofQFIs)) OF QFI OPTIONAL,
   ...
}

DRB-ToAddMod ::= SEQUENCE {
   cnAssociation [0] EXPLICIT CHOICE {
      eps-BearerIdentity [0] INTEGER (0..15),
      sdap-Config [1] SDAP-Config
   } OPTIONAL, -- Cond DRBSetup
   drb-Identity [1] DRB-Identity,
   reestablishPDCP [2] ENUMERATED { true(0) } OPTIONAL, -- Need N
   recoverPDCP [3] ENUMERATED { true(0) } OPTIONAL, -- Need N
   pdcp-Config [4] PDCP-Config OPTIONAL,
   ...,
   [[
      daps-Config-r16 [5] ENUMERATED { true(0) } OPTIONAL
   ]]
}

DRB-ToAddModList ::= SEQUENCE (SIZE (1..maxDRB)) OF DRB-ToAddMod

DRB-ToReleaseList ::= SEQUENCE (SIZE (1..maxDRB)) OF DRB-Identity

-- TAG-SEARCHSPACEZERO-STOP
-- TAG-SECURITYALGORITHMCONFIG-START
SecurityAlgorithmConfig ::= SEQUENCE {
   cipheringAlgorithm [0] CipheringAlgorithm,
   integrityProtAlgorithm [1] IntegrityProtAlgorithm OPTIONAL,
   ...
}

SecurityConfig ::= SEQUENCE {
   securityAlgorithmConfig [0] SecurityAlgorithmConfig OPTIONAL, -- Cond RBTermChange1
   keyToUse [1] ENUMERATED { master(0), secondary(1) } OPTIONAL,
   ...
}

-- TAG-PDSCH-CONFIGBROADCAST-STOP
-- TAG-TMGI-START
TMGI-r17 ::= SEQUENCE {
   plmn-Id-r17 [0] EXPLICIT CHOICE {
      plmn-Index [0] INTEGER (1..maxPLMN),
      explicitValue [1] PLMN-Identity
   },
   serviceId-r17 [1] OCTET STRING (SIZE (3))
}

MRB-ToAddMod-r17 ::= SEQUENCE {
   mbs-SessionId-r17 [0] TMGI-r17 OPTIONAL, -- Cond MRBSetup
   mrb-Identity-r17 [1] MRB-Identity-r17,
   mrb-IdentityNew-r17 [2] MRB-Identity-r17 OPTIONAL, -- Need N
   reestablishPDCP-r17 [3] ENUMERATED { true(0) } OPTIONAL, -- Need N
   recoverPDCP-r17 [4] ENUMERATED { true(0) } OPTIONAL, -- Need N
   pdcp-Config-r17 [5] PDCP-Config OPTIONAL,
   ...
}

MRB-ToAddModList-r17 ::= SEQUENCE (SIZE (1..maxMRB-r17)) OF MRB-ToAddMod-r17

MRB-ToReleaseList-r17 ::= SEQUENCE (SIZE (1..maxMRB-r17)) OF MRB-Identity-r17

-- TAG-RA-PRIORITIZATIONFORSLICING-STOP
-- TAG-RADIOBEARERCONFIG-START
RadioBearerConfig ::= SEQUENCE {
   srb-ToAddModList [0] SRB-ToAddModList OPTIONAL, -- Cond HO-Conn
   srb3-ToRelease [1] ENUMERATED { true(0) } OPTIONAL, -- Need N
   drb-ToAddModList [2] DRB-ToAddModList OPTIONAL, -- Cond HO-toNR
   drb-ToReleaseList [3] DRB-ToReleaseList OPTIONAL, -- Need N
   securityConfig [4] SecurityConfig OPTIONAL,
   ...,
   [[
      mrb-ToAddModList-r17 [5] MRB-ToAddModList-r17 OPTIONAL,
      mrb-ToReleaseList-r17 [6] MRB-ToReleaseList-r17 OPTIONAL,
      srb4-ToAddMod-r17 [7] SRB-ToAddMod OPTIONAL,
      srb4-ToRelease-r17 [8] ENUMERATED { true(0) } OPTIONAL
   ]]
}

UL-AM-RLC ::= SEQUENCE {
   sn-FieldLength [0] SN-FieldLengthAM OPTIONAL, -- Cond Reestab
   t-PollRetransmit [1] T-PollRetransmit,
   pollPDU [2] PollPDU,
   pollByte [3] PollByte,
   maxRetxThreshold [4] ENUMERATED { t1(0), t2(1), t3(2), t4(3), t6(4), t8(5), 
      t16(6), t32(7) }
}

DL-AM-RLC ::= SEQUENCE {
   sn-FieldLength [0] SN-FieldLengthAM OPTIONAL, -- Cond Reestab
   t-Reassembly [1] T-Reassembly,
   t-StatusProhibit [2] T-StatusProhibit
}

UL-UM-RLC ::= SEQUENCE {
   sn-FieldLength [0] SN-FieldLengthUM OPTIONAL -- Cond Reestab
}

DL-UM-RLC ::= SEQUENCE {
   sn-FieldLength [0] SN-FieldLengthUM OPTIONAL, -- Cond Reestab
   t-Reassembly [1] T-Reassembly
}

-- TAG-RLC-BEARERCONFIG-STOP
-- TAG-RLC-CONFIG-START
RLC-Config ::= CHOICE {
   am [0] SEQUENCE {
      ul-AM-RLC [0] UL-AM-RLC,
      dl-AM-RLC [1] DL-AM-RLC
   },
   um-Bi-Directional [1] SEQUENCE {
      ul-UM-RLC [0] UL-UM-RLC,
      dl-UM-RLC [1] DL-UM-RLC
   },
   um-Uni-Directional-UL [2] SEQUENCE {
      ul-UM-RLC [0] UL-UM-RLC
   },
   um-Uni-Directional-DL [3] SEQUENCE {
      dl-UM-RLC [0] DL-UM-RLC
   },
   ...
}

-- TAG-LOCATIONMEASUREMENTINFO-STOP
-- TAG-LOGICALCHANNELCONFIG-START
LogicalChannelConfig ::= SEQUENCE {
   ul-SpecificParameters [0] SEQUENCE {
      priority [0] INTEGER (1..16),
      prioritisedBitRate [1] ENUMERATED { kBps0(0), kBps8(1), kBps16(2), 
         kBps32(3), kBps64(4), kBps128(5), kBps256(6), kBps512(7), kBps1024(8)
         , kBps2048(9), kBps4096(10), kBps8192(11), kBps16384(12), 
         kBps32768(13), kBps65536(14), infinity(15) },
      bucketSizeDuration [2] ENUMERATED { ms5(0), ms10(1), ms20(2), ms50(3), 
         ms100(4), ms150(5), ms300(6), ms500(7), ms1000(8), spare7(9), 
         spare6(10), spare5(11), spare4(12), spare3(13), spare2(14), spare1(15)
          },
      allowedServingCells [3] SEQUENCE (SIZE (1..maxNrofServingCells-1)) OF ServCellIndex OPTIONAL,
                                                                                                                          -- Cond PDCP-CADuplication
      allowedSCS-List [4] SEQUENCE (SIZE (1..maxSCSs)) OF SubcarrierSpacing OPTIONAL, -- Need R
      maxPUSCH-Duration [5] ENUMERATED { ms0p02(0), ms0p04(1), ms0p0625(2), 
         ms0p125(3), ms0p25(4), ms0p5(5), ms0p01-v1700(6), spare1(7) } OPTIONAL
         ,
                                                                                                                              -- Need R
      configuredGrantType1Allowed [6] ENUMERATED { true(0) } OPTIONAL, -- Need R
      logicalChannelGroup [7] INTEGER (0..maxLCG-ID) OPTIONAL, -- Need R
      schedulingRequestID [8] SchedulingRequestId OPTIONAL, -- Need R
      logicalChannelSR-Mask [9] BOOLEAN,
      logicalChannelSR-DelayTimerApplied [10] BOOLEAN,
      ...,
      bitRateQueryProhibitTimer [11] ENUMERATED { s0(0), s0dot4(1), s0dot8(2), 
         s1dot6(3), s3(4), s6(5), s12(6), s30(7) } OPTIONAL,
      [[
         allowedCG-List-r16 [12] SEQUENCE (SIZE (0..maxNrofConfiguredGrantConfigMAC-1-r16)) OF 
            ConfiguredGrantConfigIndexMAC-r16 OPTIONAL,
         allowedPHY-PriorityIndex-r16 [13] ENUMERATED { p0(0), p1(1) } OPTIONAL
      ]],
      [[
         logicalChannelGroupIAB-Ext-r17 [14] INTEGER (0..maxLCG-ID-IAB-r17) OPTIONAL,
         allowedHARQ-mode-r17 [15] ENUMERATED { harqModeA(0), harqModeB(1) }
             OPTIONAL
      ]]
   } OPTIONAL,
   ...,
   [[
      channelAccessPriority-r16 [1] INTEGER (1..4) OPTIONAL,
      bitRateMultiplier-r16 [2] ENUMERATED { x40(0), x70(1), x100(2), x200(3) }
          OPTIONAL
   ]]
}

DL-AM-RLC-v1610 ::= SEQUENCE {
   t-StatusProhibit-v1610 [0] T-StatusProhibit-v1610 OPTIONAL,
   ...
}

RLC-Config-v1610 ::= SEQUENCE {
   dl-AM-RLC-v1610 [0] DL-AM-RLC-v1610
}

DL-AM-RLC-v1700 ::= SEQUENCE {
   t-ReassemblyExt-r17 [0] T-ReassemblyExt-r17 OPTIONAL -- Need R
}

DL-UM-RLC-v1700 ::= SEQUENCE {
   t-ReassemblyExt-r17 [0] T-ReassemblyExt-r17 OPTIONAL -- Need R
}

RLC-Config-v1700 ::= SEQUENCE {
   dl-AM-RLC-v1700 [0] DL-AM-RLC-v1700,
   dl-UM-RLC-v1700 [1] DL-UM-RLC-v1700
}

MulticastRLC-BearerConfig-r17 ::= SEQUENCE {
   servedMBS-RadioBearer-r17 [0] MRB-Identity-r17,
   isPTM-Entity-r17 [1] ENUMERATED { true(0) } OPTIONAL -- Need S
}

-- TAG-RESUMECAUSE-STOP
-- TAG-RLC-BEARERCONFIG-START
RLC-BearerConfig ::= SEQUENCE {
   logicalChannelIdentity [0] LogicalChannelIdentity,
   servedRadioBearer [1] EXPLICIT CHOICE {
      srb-Identity [0] SRB-Identity,
      drb-Identity [1] DRB-Identity
   } OPTIONAL, -- Cond LCH-SetupOnly
   reestablishRLC [2] ENUMERATED { true(0) } OPTIONAL, -- Need N
   rlc-Config [3] EXPLICIT RLC-Config OPTIONAL, -- Cond LCH-Setup
   mac-LogicalChannelConfig [4] LogicalChannelConfig OPTIONAL,
   ...,
   [[
      rlc-Config-v1610 [5] RLC-Config-v1610 OPTIONAL
   ]],
   [[
      rlc-Config-v1700 [6] RLC-Config-v1700 OPTIONAL,
      logicalChannelIdentityExt-r17 [7] LogicalChannelIdentityExt-r17 OPTIONAL
         ,
      multicastRLC-BearerConfig-r17 [8] MulticastRLC-BearerConfig-r17 OPTIONAL
         ,
      servedRadioBearerSRB4-r17 [9] SRB-Identity-v1700 OPTIONAL
   ]]
}

-- TAG-DRB-IDENTITY-STOP
-- TAG-DRX-CONFIG-START
DRX-Config ::= SEQUENCE {
   drx-onDurationTimer [0] EXPLICIT CHOICE {
      subMilliSeconds [0] INTEGER (1..31),
      milliSeconds [1] ENUMERATED { ms1(0), ms2(1), ms3(2), ms4(3), ms5(4), 
         ms6(5), ms8(6), ms10(7), ms20(8), ms30(9), ms40(10), ms50(11), 
         ms60(12), ms80(13), ms100(14), ms200(15), ms300(16), ms400(17), 
         ms500(18), ms600(19), ms800(20), ms1000(21), ms1200(22), ms1600(23), 
         spare8(24), spare7(25), spare6(26), spare5(27), spare4(28), spare3(29)
         , spare2(30), spare1(31) }
   },
   drx-InactivityTimer [1] ENUMERATED { ms0(0), ms1(1), ms2(2), ms3(3), ms4(4)
      , ms5(5), ms6(6), ms8(7), ms10(8), ms20(9), ms30(10), ms40(11), ms50(12)
      , ms60(13), ms80(14), ms100(15), ms200(16), ms300(17), ms500(18), 
      ms750(19), ms1280(20), ms1920(21), ms2560(22), spare9(23), spare8(24), 
      spare7(25), spare6(26), spare5(27), spare4(28), spare3(29), spare2(30), 
      spare1(31) },
   drx-HARQ-RTT-TimerDL [2] INTEGER (0..56),
   drx-HARQ-RTT-TimerUL [3] INTEGER (0..56),
   drx-RetransmissionTimerDL [4] ENUMERATED { sl0(0), sl1(1), sl2(2), sl4(3), 
      sl6(4), sl8(5), sl16(6), sl24(7), sl33(8), sl40(9), sl64(10), sl80(11), 
      sl96(12), sl112(13), sl128(14), sl160(15), sl320(16), spare15(17), 
      spare14(18), spare13(19), spare12(20), spare11(21), spare10(22), 
      spare9(23), spare8(24), spare7(25), spare6(26), spare5(27), spare4(28), 
      spare3(29), spare2(30), spare1(31) },
   drx-RetransmissionTimerUL [5] ENUMERATED { sl0(0), sl1(1), sl2(2), sl4(3), 
      sl6(4), sl8(5), sl16(6), sl24(7), sl33(8), sl40(9), sl64(10), sl80(11), 
      sl96(12), sl112(13), sl128(14), sl160(15), sl320(16), spare15(17), 
      spare14(18), spare13(19), spare12(20), spare11(21), spare10(22), 
      spare9(23), spare8(24), spare7(25), spare6(26), spare5(27), spare4(28), 
      spare3(29), spare2(30), spare1(31) },
   drx-LongCycleStartOffset [6] EXPLICIT CHOICE {
      ms10 [0] INTEGER (0..9),
      ms20 [1] INTEGER (0..19),
      ms32 [2] INTEGER (0..31),
      ms40 [3] INTEGER (0..39),
      ms60 [4] INTEGER (0..59),
      ms64 [5] INTEGER (0..63),
      ms70 [6] INTEGER (0..69),
      ms80 [7] INTEGER (0..79),
      ms128 [8] INTEGER (0..127),
      ms160 [9] INTEGER (0..159),
      ms256 [10] INTEGER (0..255),
      ms320 [11] INTEGER (0..319),
      ms512 [12] INTEGER (0..511),
      ms640 [13] INTEGER (0..639),
      ms1024 [14] INTEGER (0..1023),
      ms1280 [15] INTEGER (0..1279),
      ms2048 [16] INTEGER (0..2047),
      ms2560 [17] INTEGER (0..2559),
      ms5120 [18] INTEGER (0..5119),
      ms10240 [19] INTEGER (0..10239)
   },
   shortDRX [7] SEQUENCE {
      drx-ShortCycle [0] ENUMERATED { ms2(0), ms3(1), ms4(2), ms5(3), ms6(4), 
         ms7(5), ms8(6), ms10(7), ms14(8), ms16(9), ms20(10), ms30(11), 
         ms32(12), ms35(13), ms40(14), ms64(15), ms80(16), ms128(17), ms160(18)
         , ms256(19), ms320(20), ms512(21), ms640(22), spare9(23), spare8(24), 
         spare7(25), spare6(26), spare5(27), spare4(28), spare3(29), spare2(30)
         , spare1(31) },
      drx-ShortCycleTimer [1] INTEGER (1..16)
   } OPTIONAL, -- Need R
   drx-SlotOffset [8] INTEGER (0..31)
}

SchedulingRequestToAddMod ::= SEQUENCE {
   schedulingRequestId [0] SchedulingRequestId,
   sr-ProhibitTimer [1] ENUMERATED { ms1(0), ms2(1), ms4(2), ms8(3), ms16(4), 
      ms32(5), ms64(6), ms128(7) } OPTIONAL, -- Need S
   sr-TransMax [2] ENUMERATED { n4(0), n8(1), n16(2), n32(3), n64(4), spare3(5)
      , spare2(6), spare1(7) }
}

-- TAG-SCELLINDEX-STOP
-- TAG-SCHEDULINGREQUESTCONFIG-START
SchedulingRequestConfig ::= SEQUENCE {
   schedulingRequestToAddModList [0] SEQUENCE (SIZE (1..maxNrofSR-ConfigPerCellGroup)) OF 
      SchedulingRequestToAddMod OPTIONAL,
                                                                                                                     -- Need N
   schedulingRequestToReleaseList [1] SEQUENCE (SIZE (1..maxNrofSR-ConfigPerCellGroup)) OF 
      SchedulingRequestId OPTIONAL
                                                                                                                     -- Need N
}

-- TAG-BHRLCCHANNELID-STOP
-- TAG-BSR-CONFIG-START
BSR-Config ::= SEQUENCE {
   periodicBSR-Timer [0] ENUMERATED { sf1(0), sf5(1), sf10(2), sf16(3), sf20(4)
      , sf32(5), sf40(6), sf64(7), sf80(8), sf128(9), sf160(10), sf320(11), 
      sf640(12), sf1280(13), sf2560(14), infinity(15) },
   retxBSR-Timer [1] ENUMERATED { sf10(0), sf20(1), sf40(2), sf80(3), sf160(4)
      , sf320(5), sf640(6), sf1280(7), sf2560(8), sf5120(9), sf10240(10), 
      spare5(11), spare4(12), spare3(13), spare2(14), spare1(15) },
   logicalChannelSR-DelayTimer [2] ENUMERATED { sf20(0), sf40(1), sf64(2), 
      sf128(3), sf512(4), sf1024(5), sf2560(6), spare1(7) } OPTIONAL,
   ...
}

TAG ::= SEQUENCE {
   tag-Id [0] TAG-Id,
   timeAlignmentTimer [1] TimeAlignmentTimer,
   ...
}

-- TAG-SUBCARRIERSPACING-STOP
-- TAG-TAG-CONFIG-START
TAG-Config ::= SEQUENCE {
   tag-ToReleaseList [0] SEQUENCE (SIZE (1..maxNrofTAGs)) OF TAG-Id OPTIONAL, -- Need N
   tag-ToAddModList [1] SEQUENCE (SIZE (1..maxNrofTAGs)) OF TAG OPTIONAL -- Need N
}

MPE-Config-FR2-r16 ::= SEQUENCE {
   mpe-ProhibitTimer-r16 [0] ENUMERATED { sf0(0), sf10(1), sf20(2), sf50(3), 
      sf100(4), sf200(5), sf500(6), sf1000(7) },
   mpe-Threshold-r16 [1] ENUMERATED { dB3(0), dB6(1), dB9(2), dB12(3) }
}

MPE-Config-FR2-r17 ::= SEQUENCE {
   mpe-ProhibitTimer-r17 [0] ENUMERATED { sf0(0), sf10(1), sf20(2), sf50(3), 
      sf100(4), sf200(5), sf500(6), sf1000(7) },
   mpe-Threshold-r17 [1] ENUMERATED { dB3(0), dB6(1), dB9(2), dB12(3) },
   numberOfN-r17 [2] INTEGER (1..4),
   ...
}

-- TAG-PDSCH-TIMEDOMAINRESOURCEALLOCATIONLIST-STOP
-- TAG-PHR-CONFIG-START
PHR-Config ::= SEQUENCE {
   phr-PeriodicTimer [0] ENUMERATED { sf10(0), sf20(1), sf50(2), sf100(3), 
      sf200(4), sf500(5), sf1000(6), infinity(7) },
   phr-ProhibitTimer [1] ENUMERATED { sf0(0), sf10(1), sf20(2), sf50(3), 
      sf100(4), sf200(5), sf500(6), sf1000(7) },
   phr-Tx-PowerFactorChange [2] ENUMERATED { dB1(0), dB3(1), dB6(2), 
      infinity(3) },
   multiplePHR [3] BOOLEAN,
   dummy [4] BOOLEAN,
   phr-Type2OtherCell [5] BOOLEAN,
   phr-ModeOtherCG [6] ENUMERATED { real(0), virtual(1) },
   ...,
   [[
      mpe-Reporting-FR2-r16 [7] EXPLICIT CHOICE {
         release [0] NULL,
         setup [1] EXPLICIT MPE-Config-FR2-r16
      } OPTIONAL
   ]],
   [[
      mpe-Reporting-FR2-r17 [8] EXPLICIT CHOICE {
         release [0] NULL,
         setup [1] EXPLICIT MPE-Config-FR2-r17
      } OPTIONAL,
      twoPHRMode-r17 [9] ENUMERATED { enabled(0) } OPTIONAL
   ]]
}

-- TAG-DRX-CONFIG-STOP
-- TAG-DRX-CONFIGSECONDARYGROUP-START
DRX-ConfigSecondaryGroup-r16 ::= SEQUENCE {
   drx-onDurationTimer-r16 [0] EXPLICIT CHOICE {
      subMilliSeconds [0] INTEGER (1..31),
      milliSeconds [1] ENUMERATED { ms1(0), ms2(1), ms3(2), ms4(3), ms5(4), 
         ms6(5), ms8(6), ms10(7), ms20(8), ms30(9), ms40(10), ms50(11), 
         ms60(12), ms80(13), ms100(14), ms200(15), ms300(16), ms400(17), 
         ms500(18), ms600(19), ms800(20), ms1000(21), ms1200(22), ms1600(23), 
         spare8(24), spare7(25), spare6(26), spare5(27), spare4(28), spare3(29)
         , spare2(30), spare1(31) }
   },
   drx-InactivityTimer-r16 [1] ENUMERATED { ms0(0), ms1(1), ms2(2), ms3(3), 
      ms4(4), ms5(5), ms6(6), ms8(7), ms10(8), ms20(9), ms30(10), ms40(11), 
      ms50(12), ms60(13), ms80(14), ms100(15), ms200(16), ms300(17), ms500(18)
      , ms750(19), ms1280(20), ms1920(21), ms2560(22), spare9(23), spare8(24), 
      spare7(25), spare6(26), spare5(27), spare4(28), spare3(29), spare2(30), 
      spare1(31) }
}

-- TAG-DRX-CONFIGSECONDARYGROUP-STOP
-- TAG-DRX-CONFIGSL-START
DRX-ConfigSL-r17 ::= SEQUENCE {
   drx-HARQ-RTT-TimerSL-r17 [0] INTEGER (0..56),
   drx-RetransmissionTimerSL-r17 [1] ENUMERATED { sl0(0), sl1(1), sl2(2), 
      sl4(3), sl6(4), sl8(5), sl16(6), sl24(7), sl33(8), sl40(9), sl64(10), 
      sl80(11), sl96(12), sl112(13), sl128(14), sl160(15), sl320(16), 
      spare15(17), spare14(18), spare13(19), spare12(20), spare11(21), 
      spare10(22), spare9(23), spare8(24), spare7(25), spare6(26), spare5(27), 
      spare4(28), spare3(29), spare2(30), spare1(31) }
}

DRX-ConfigExt-v1700 ::= SEQUENCE {
   drx-HARQ-RTT-TimerDL-r17 [0] INTEGER (0..448),
   drx-HARQ-RTT-TimerUL-r17 [1] INTEGER (0..448)
}

SchedulingRequestToAddModExt-v1700 ::= SEQUENCE {
   sr-ProhibitTimer-v1700 [0] ENUMERATED { ms192(0), ms256(1), ms320(2), 
      ms384(3), ms448(4), ms512(5), ms576(6), ms640(7), ms1082(8), spare7(9), 
      spare6(10), spare5(11), spare4(12), spare3(13), spare2(14), spare1(15) }
       OPTIONAL
                                                                                                                     -- Need R
}

SchedulingRequestConfig-v1700 ::= SEQUENCE {
   schedulingRequestToAddModListExt-v1700 [0] SEQUENCE (SIZE (1..maxNrofSR-ConfigPerCellGroup)) OF 
      SchedulingRequestToAddModExt-v1700 OPTIONAL
                                                                                                                     -- Need N
}

-- TAG-TAG-CONFIG-STOP
-- TAG-TAR-CONFIG-START
TAR-Config-r17 ::= SEQUENCE {
   offsetThresholdTA-r17 [0] ENUMERATED { ms0dot5(0), ms1(1), ms2(2), ms3(3), 
      ms4(4), ms5(5), ms6(6), ms7(7), ms8(8), ms9(9), ms10(10), ms11(11), 
      ms12(12), ms13(13), ms14(14), ms15(15), spare13(16), spare12(17), 
      spare11(18), spare10(19), spare9(20), spare8(21), spare7(22), spare6(23)
      , spare5(24), spare4(25), spare3(26), spare2(27), spare1(28) } OPTIONAL, -- Need R
   timingAdvanceSR-r17 [1] ENUMERATED { enabled(0) } OPTIONAL,
   ...
}

-- TAG-CFR-CONFIGMCCH-MTCH-STOP
-- TAG-DRX-CONFIGPTM-START
DRX-ConfigPTM-r17 ::= SEQUENCE {
   drx-onDurationTimerPTM-r17 [0] EXPLICIT CHOICE {
      subMilliSeconds [0] INTEGER (1..31),
      milliSeconds [1] ENUMERATED { ms1(0), ms2(1), ms3(2), ms4(3), ms5(4), 
         ms6(5), ms8(6), ms10(7), ms20(8), ms30(9), ms40(10), ms50(11), 
         ms60(12), ms80(13), ms100(14), ms200(15), ms300(16), ms400(17), 
         ms500(18), ms600(19), ms800(20), ms1000(21), ms1200(22), ms1600(23), 
         spare8(24), spare7(25), spare6(26), spare5(27), spare4(28), spare3(29)
         , spare2(30), spare1(31) }
   },
   drx-InactivityTimerPTM-r17 [1] ENUMERATED { ms0(0), ms1(1), ms2(2), ms3(3), 
      ms4(4), ms5(5), ms6(6), ms8(7), ms10(8), ms20(9), ms30(10), ms40(11), 
      ms50(12), ms60(13), ms80(14), ms100(15), ms200(16), ms300(17), ms500(18)
      , ms750(19), ms1280(20), ms1920(21), ms2560(22), spare9(23), spare8(24), 
      spare7(25), spare6(26), spare5(27), spare4(28), spare3(29), spare2(30), 
      spare1(31) },
   drx-HARQ-RTT-TimerDL-PTM-r17 [2] INTEGER (0..56) OPTIONAL, -- Cond HARQFeedback
   drx-RetransmissionTimerDL-PTM-r17 [3] ENUMERATED { sl0(0), sl1(1), sl2(2), 
      sl4(3), sl6(4), sl8(5), sl16(6), sl24(7), sl33(8), sl40(9), sl64(10), 
      sl80(11), sl96(12), sl112(13), sl128(14), sl160(15), sl320(16), 
      spare15(17), spare14(18), spare13(19), spare12(20), spare11(21), 
      spare10(22), spare9(23), spare8(24), spare7(25), spare6(26), spare5(27), 
      spare4(28), spare3(29), spare2(30), spare1(31) } OPTIONAL, -- Cond HARQFeedback
   drx-LongCycleStartOffsetPTM-r17 [4] EXPLICIT CHOICE {
      ms10 [0] INTEGER (0..9),
      ms20 [1] INTEGER (0..19),
      ms32 [2] INTEGER (0..31),
      ms40 [3] INTEGER (0..39),
      ms60 [4] INTEGER (0..59),
      ms64 [5] INTEGER (0..63),
      ms70 [6] INTEGER (0..69),
      ms80 [7] INTEGER (0..79),
      ms128 [8] INTEGER (0..127),
      ms160 [9] INTEGER (0..159),
      ms256 [10] INTEGER (0..255),
      ms320 [11] INTEGER (0..319),
      ms512 [12] INTEGER (0..511),
      ms640 [13] INTEGER (0..639),
      ms1024 [14] INTEGER (0..1023),
      ms1280 [15] INTEGER (0..1279),
      ms2048 [16] INTEGER (0..2047),
      ms2560 [17] INTEGER (0..2559),
      ms5120 [18] INTEGER (0..5119),
      ms10240 [19] INTEGER (0..10239)
   },
   drx-SlotOffsetPTM-r17 [5] INTEGER (0..31)
}

MBS-RNTI-SpecificConfig-r17 ::= SEQUENCE {
   mbs-RNTI-SpecificConfigId-r17 [0] MBS-RNTI-SpecificConfigId-r17,
   groupCommon-RNTI-r17 [1] EXPLICIT CHOICE {
      g-RNTI [0] RNTI-Value,
      g-CS-RNTI [1] RNTI-Value
   },
   drx-ConfigPTM-r17 [2] EXPLICIT CHOICE {
      release [0] NULL,
      setup [1] EXPLICIT DRX-ConfigPTM-r17
   } OPTIONAL, -- Need M
   harq-FeedbackEnablerMulticast-r17 [3] ENUMERATED { dci-enabler(0), 
      enabled(1) } OPTIONAL, -- Need S
   harq-FeedbackOptionMulticast-r17 [4] ENUMERATED { ack-nack(0), nack-only(1)
       } OPTIONAL, -- Cond HARQFeedback
   pdsch-AggregationFactor-r17 [5] ENUMERATED { n2(0), n4(1), n8(2) } OPTIONAL -- Cond G-RNTI
}

-- TAG-LTE-NEIGHCELLSCRS-ASSISTINFOLIST-STOP
-- TAG-MAC-CELLGROUPCONFIG-START
MAC-CellGroupConfig ::= SEQUENCE {
   drx-Config [0] EXPLICIT CHOICE {
      release [0] NULL,
      setup [1] EXPLICIT DRX-Config
   } OPTIONAL, -- Need M
   schedulingRequestConfig [1] SchedulingRequestConfig OPTIONAL, -- Need M
   bsr-Config [2] BSR-Config OPTIONAL, -- Need M
   tag-Config [3] TAG-Config OPTIONAL, -- Need M
   phr-Config [4] EXPLICIT CHOICE {
      release [0] NULL,
      setup [1] EXPLICIT PHR-Config
   } OPTIONAL, -- Need M
   skipUplinkTxDynamic [5] BOOLEAN,
   ...,
   [[
      csi-Mask [6] BOOLEAN OPTIONAL,
      dataInactivityTimer [7] EXPLICIT CHOICE {
         release [0] NULL,
         setup [1] EXPLICIT DataInactivityTimer
      } OPTIONAL
   ]],
   [[
      usePreBSR-r16 [8] ENUMERATED { true(0) } OPTIONAL,
      schedulingRequestID-LBT-SCell-r16 [9] SchedulingRequestId OPTIONAL,
      lch-BasedPrioritization-r16 [10] ENUMERATED { enabled(0) } OPTIONAL,
      schedulingRequestID-BFR-SCell-r16 [11] SchedulingRequestId OPTIONAL,
      drx-ConfigSecondaryGroup-r16 [12] EXPLICIT CHOICE {
         release [0] NULL,
         setup [1] EXPLICIT DRX-ConfigSecondaryGroup-r16
      } OPTIONAL
   ]],
   [[
      enhancedSkipUplinkTxDynamic-r16 [13] ENUMERATED { true(0) } OPTIONAL,
      enhancedSkipUplinkTxConfigured-r16 [14] ENUMERATED { true(0) } OPTIONAL
   ]],
   [[
      intraCG-Prioritization-r17 [15] ENUMERATED { enabled(0) } OPTIONAL,
      drx-ConfigSL-r17 [16] EXPLICIT CHOICE {
         release [0] NULL,
         setup [1] EXPLICIT DRX-ConfigSL-r17
      } OPTIONAL,
      drx-ConfigExt-v1700 [17] EXPLICIT CHOICE {
         release [0] NULL,
         setup [1] EXPLICIT DRX-ConfigExt-v1700
      } OPTIONAL,
      schedulingRequestID-BFR-r17 [18] SchedulingRequestId OPTIONAL,
      schedulingRequestID-BFR2-r17 [19] SchedulingRequestId OPTIONAL,
      schedulingRequestConfig-v1700 [20] SchedulingRequestConfig-v1700 OPTIONAL
         ,
      tar-Config-r17 [21] EXPLICIT CHOICE {
         release [0] NULL,
         setup [1] EXPLICIT TAR-Config-r17
      } OPTIONAL,
      g-RNTI-ConfigToAddModList-r17 [22] SEQUENCE (SIZE (1..maxG-RNTI-r17)) OF 
         MBS-RNTI-SpecificConfig-r17 OPTIONAL,
      g-RNTI-ConfigToReleaseList-r17 [23] SEQUENCE (SIZE (1..maxG-RNTI-r17)) OF 
         MBS-RNTI-SpecificConfigId-r17 OPTIONAL,
      g-CS-RNTI-ConfigToAddModList-r17 [24] SEQUENCE (SIZE (1..maxG-CS-RNTI-r17)) OF 
         MBS-RNTI-SpecificConfig-r17 OPTIONAL,
      g-CS-RNTI-ConfigToReleaseList-r17 [25] SEQUENCE (SIZE (1..maxG-CS-RNTI-r17)) OF 
         MBS-RNTI-SpecificConfigId-r17 OPTIONAL,
      allowCSI-SRS-Tx-MulticastDRX-Active-r17 [26] BOOLEAN OPTIONAL
   ]],
   [[
      schedulingRequestID-PosMG-Request-r17 [27] SchedulingRequestId OPTIONAL,
      drx-LastTransmissionUL-r17 [28] ENUMERATED { enabled(0) } OPTIONAL
   ]],
   [[
      posMG-Request-r17 [29] ENUMERATED { enabled(0) } OPTIONAL
   ]]
}

DCP-Config-r16 ::= SEQUENCE {
   ps-RNTI-r16 [0] RNTI-Value,
   ps-Offset-r16 [1] INTEGER (1..120),
   sizeDCI-2-6-r16 [2] INTEGER (1..maxDCI-2-6-Size-r16),
   ps-PositionDCI-2-6-r16 [3] INTEGER (0..maxDCI-2-6-Size-1-r16),
   ps-WakeUp-r16 [4] ENUMERATED { true(0) } OPTIONAL, -- Need S
   ps-TransmitPeriodicL1-RSRP-r16 [5] ENUMERATED { true(0) } OPTIONAL, -- Need S
   ps-TransmitOtherPeriodicCSI-r16 [6] ENUMERATED { true(0) } OPTIONAL -- Need S
}

PDSCH-HARQ-ACK-CodebookList-r16 ::= SEQUENCE (SIZE (1..2)) OF ENUMERATED { 
   semiStatic(0), dynamic(1) }

PDCCH-BlindDetectionCA-CombIndicator-r16 ::= SEQUENCE {
   pdcch-BlindDetectionCA1-r16 [0] INTEGER (1..15),
   pdcch-BlindDetectionCA2-r16 [1] INTEGER (1..15)
}

PDSCH-HARQ-ACK-EnhType3-r17 ::= SEQUENCE {
   pdsch-HARQ-ACK-EnhType3Index-r17 [0] PDSCH-HARQ-ACK-EnhType3Index-r17,
   applicable-r17 [1] EXPLICIT CHOICE {
      perCC [0] SEQUENCE (SIZE (1..maxNrofServingCells)) OF INTEGER (0..1),
      perHARQ [1] SEQUENCE (SIZE (1..maxNrofServingCells)) OF BIT STRING  (SIZE (16))
   },
   pdsch-HARQ-ACK-EnhType3NDI-r17 [2] ENUMERATED { true(0) } OPTIONAL, -- Need R
   pdsch-HARQ-ACK-EnhType3CBG-r17 [3] ENUMERATED { true(0) } OPTIONAL,
   ...,
   [[
      perHARQ-Ext-r17 [4] SEQUENCE (SIZE (1..maxNrofServingCells)) OF BIT STRING  (SIZE (32))
          OPTIONAL
   ]]
}

MulticastConfig-r17 ::= SEQUENCE {
   pdsch-HARQ-ACK-CodebookListMulticast-r17 [0] EXPLICIT CHOICE {
      release [0] NULL,
      setup [1] EXPLICIT PDSCH-HARQ-ACK-CodebookList-r16
   } OPTIONAL, -- Need M
   type1CodebookGenerationMode-r17 [1] ENUMERATED { mode1(0), mode2(1) }
       OPTIONAL -- Need M
}

PDCCH-BlindDetectionCA-CombIndicator-r17 ::= SEQUENCE {
   pdcch-BlindDetectionCA1-r17 [0] INTEGER (1..15) OPTIONAL, -- Need R
   pdcch-BlindDetectionCA2-r17 [1] INTEGER (1..15) OPTIONAL, -- Need R
   pdcch-BlindDetectionCA3-r17 [2] INTEGER (1..15)
}

-- TAG-PHYSCELLID-STOP
-- TAG-PHYSICALCELLGROUPCONFIG-START
PhysicalCellGroupConfig ::= SEQUENCE {
   harq-ACK-SpatialBundlingPUCCH [0] ENUMERATED { true(0) } OPTIONAL, -- Need S
   harq-ACK-SpatialBundlingPUSCH [1] ENUMERATED { true(0) } OPTIONAL, -- Need S
   p-NR-FR1 [2] P-Max OPTIONAL, -- Need R
   pdsch-HARQ-ACK-Codebook [3] ENUMERATED { semiStatic(0), dynamic(1) },
   tpc-SRS-RNTI [4] RNTI-Value OPTIONAL, -- Need R
   tpc-PUCCH-RNTI [5] RNTI-Value OPTIONAL, -- Need R
   tpc-PUSCH-RNTI [6] RNTI-Value OPTIONAL, -- Need R
   sp-CSI-RNTI [7] RNTI-Value OPTIONAL, -- Need R
   cs-RNTI [8] EXPLICIT CHOICE {
      release [0] NULL,
      setup [1] EXPLICIT RNTI-Value
   } OPTIONAL,
   ...,
   [[
      mcs-C-RNTI [9] RNTI-Value OPTIONAL,
      p-UE-FR1 [10] P-Max OPTIONAL
   ]],
   [[
      xScale [11] ENUMERATED { dB0(0), dB6(1), spare2(2), spare1(3) } OPTIONAL
   ]],
   [[
      pdcch-BlindDetection [12] EXPLICIT CHOICE {
         release [0] NULL,
         setup [1] EXPLICIT PDCCH-BlindDetection
      } OPTIONAL
   ]],
   [[
      dcp-Config-r16 [13] EXPLICIT CHOICE {
         release [0] NULL,
         setup [1] EXPLICIT DCP-Config-r16
      } OPTIONAL,
      harq-ACK-SpatialBundlingPUCCH-secondaryPUCCHgroup-r16 [14] ENUMERATED { 
         enabled(0), disabled(1) } OPTIONAL,
      harq-ACK-SpatialBundlingPUSCH-secondaryPUCCHgroup-r16 [15] ENUMERATED { 
         enabled(0), disabled(1) } OPTIONAL,
      pdsch-HARQ-ACK-Codebook-secondaryPUCCHgroup-r16 [16] ENUMERATED { 
         semiStatic(0), dynamic(1) } OPTIONAL,
      p-NR-FR2-r16 [17] P-Max OPTIONAL,
      p-UE-FR2-r16 [18] P-Max OPTIONAL,
      nrdc-PCmode-FR1-r16 [19] ENUMERATED { semi-static-mode1(0), 
         semi-static-mode2(1), dynamic(2) } OPTIONAL,
      nrdc-PCmode-FR2-r16 [20] ENUMERATED { semi-static-mode1(0), 
         semi-static-mode2(1), dynamic(2) } OPTIONAL,
      pdsch-HARQ-ACK-Codebook-r16 [21] ENUMERATED { enhancedDynamic(0) }
          OPTIONAL,
      nfi-TotalDAI-Included-r16 [22] ENUMERATED { true(0) } OPTIONAL,
      ul-TotalDAI-Included-r16 [23] ENUMERATED { true(0) } OPTIONAL,
      pdsch-HARQ-ACK-OneShotFeedback-r16 [24] ENUMERATED { true(0) } OPTIONAL,
      pdsch-HARQ-ACK-OneShotFeedbackNDI-r16 [25] ENUMERATED { true(0) }
          OPTIONAL,
      pdsch-HARQ-ACK-OneShotFeedbackCBG-r16 [26] ENUMERATED { true(0) }
          OPTIONAL,
      downlinkAssignmentIndexDCI-0-2-r16 [27] ENUMERATED { enabled(0) }
          OPTIONAL,
      downlinkAssignmentIndexDCI-1-2-r16 [28] ENUMERATED { n1(0), n2(1), n4(2)
          } OPTIONAL,
      pdsch-HARQ-ACK-CodebookList-r16 [29] EXPLICIT CHOICE {
         release [0] NULL,
         setup [1] EXPLICIT PDSCH-HARQ-ACK-CodebookList-r16
      } OPTIONAL,
      ackNackFeedbackMode-r16 [30] ENUMERATED { joint(0), separate(1) }
          OPTIONAL,
      pdcch-BlindDetectionCA-CombIndicator-r16 [31] EXPLICIT CHOICE {
         release [0] NULL,
         setup [1] EXPLICIT PDCCH-BlindDetectionCA-CombIndicator-r16
      } OPTIONAL,
      pdcch-BlindDetection2-r16 [32] EXPLICIT CHOICE {
         release [0] NULL,
         setup [1] EXPLICIT PDCCH-BlindDetection2-r16
      } OPTIONAL,
      pdcch-BlindDetection3-r16 [33] EXPLICIT CHOICE {
         release [0] NULL,
         setup [1] EXPLICIT PDCCH-BlindDetection3-r16
      } OPTIONAL,
      bdFactorR-r16 [34] ENUMERATED { n1(0) } OPTIONAL
   ]],
   [[
      pdsch-HARQ-ACK-EnhType3ToAddModList-r17 [35] SEQUENCE (SIZE (1..maxNrofEnhType3HARQ-ACK-r17)) OF 
         PDSCH-HARQ-ACK-EnhType3-r17 OPTIONAL,
      pdsch-HARQ-ACK-EnhType3ToReleaseList-r17 [36] SEQUENCE (SIZE (1..maxNrofEnhType3HARQ-ACK-r17)) OF 
         PDSCH-HARQ-ACK-EnhType3Index-r17 OPTIONAL,
      pdsch-HARQ-ACK-EnhType3SecondaryToAddModList-r17 [37] SEQUENCE (SIZE (1..maxNrofEnhType3HARQ-ACK-r17)
         ) OF PDSCH-HARQ-ACK-EnhType3-r17 OPTIONAL,
      pdsch-HARQ-ACK-EnhType3SecondaryToReleaseList-r17 [38] SEQUENCE (SIZE (1..maxNrofEnhType3HARQ-ACK-r17
         )) OF PDSCH-HARQ-ACK-EnhType3Index-r17 OPTIONAL,
      pdsch-HARQ-ACK-EnhType3DCI-FieldSecondaryPUCCHgroup-r17 [39] ENUMERATED
          { enabled(0) } OPTIONAL,
      pdsch-HARQ-ACK-EnhType3DCI-Field-r17 [40] ENUMERATED { enabled(0) }
          OPTIONAL,
      pdsch-HARQ-ACK-Retx-r17 [41] ENUMERATED { enabled(0) } OPTIONAL,
      pdsch-HARQ-ACK-RetxSecondaryPUCCHgroup-r17 [42] ENUMERATED { enabled(0) }
          OPTIONAL,
      pucch-sSCell-r17 [43] SCellIndex OPTIONAL,
      pucch-sSCellSecondaryPUCCHgroup-r17 [44] SCellIndex OPTIONAL,
      pucch-sSCellDyn-r17 [45] ENUMERATED { enabled(0) } OPTIONAL,
      pucch-sSCellDynSecondaryPUCCHgroup-r17 [46] ENUMERATED { enabled(0) }
          OPTIONAL,
      pucch-sSCellPattern-r17 [47] SEQUENCE (SIZE (1..maxNrofSlots)) OF INTEGER (0..1)
          OPTIONAL,
      pucch-sSCellPatternSecondaryPUCCHgroup-r17 [48] SEQUENCE (SIZE (1..maxNrofSlots)) OF 
         INTEGER (0..1) OPTIONAL,
      uci-MuxWithDiffPrio-r17 [49] ENUMERATED { enabled(0) } OPTIONAL,
      uci-MuxWithDiffPrioSecondaryPUCCHgroup-r17 [50] ENUMERATED { enabled(0) }
          OPTIONAL,
      simultaneousPUCCH-PUSCH-r17 [51] ENUMERATED { enabled(0) } OPTIONAL,
      simultaneousPUCCH-PUSCH-SecondaryPUCCHgroup-r17 [52] ENUMERATED { 
         enabled(0) } OPTIONAL,
      prioLowDG-HighCG-r17 [53] ENUMERATED { enabled(0) } OPTIONAL,
      prioHighDG-LowCG-r17 [54] ENUMERATED { enabled(0) } OPTIONAL,
      twoQCLTypeDforPDCCHRepetition-r17 [55] ENUMERATED { enabled(0) } OPTIONAL
         ,
      multicastConfig-r17 [56] EXPLICIT CHOICE {
         release [0] NULL,
         setup [1] EXPLICIT MulticastConfig-r17
      } OPTIONAL,
      pdcch-BlindDetectionCA-CombIndicator-r17 [57] EXPLICIT CHOICE {
         release [0] NULL,
         setup [1] EXPLICIT PDCCH-BlindDetectionCA-CombIndicator-r17
      } OPTIONAL
   ]],
   [[
      simultaneousSR-PUSCH-diffPUCCH-Groups-r17 [58] ENUMERATED { enabled(0) }
          OPTIONAL
   ]],
   [[
      intraBandNC-PRACH-simulTx-r17 [59] ENUMERATED { enabled(0) } OPTIONAL
   ]],
   [[
      pdcch-BlindDetection4-r17 [60] EXPLICIT CHOICE {
         release [0] NULL,
         setup [1] EXPLICIT PDCCH-BlindDetection4-r17
      } OPTIONAL
   ]],
   [[
      simultaneousPUCCH-PUSCH-SamePriority-r17 [61] ENUMERATED { enabled(0) }
          OPTIONAL,
      simultaneousPUCCH-PUSCH-SamePriority-SecondaryPUCCHgroup-r17 [62] 
         ENUMERATED { enabled(0) } OPTIONAL
   ]]
}

-- TAG-FREQPRIORITYLISTSLICING-STOP
-- TAG-FREQUENCYINFODL-START
FrequencyInfoDL ::= SEQUENCE {
   absoluteFrequencySSB [0] ARFCN-ValueNR OPTIONAL, -- Cond SpCellAdd
   frequencyBandList [1] MultiFrequencyBandListNR,
   absoluteFrequencyPointA [2] ARFCN-ValueNR,
   scs-SpecificCarrierList [3] SEQUENCE (SIZE (1..maxSCSs)) OF SCS-SpecificCarrier,
   ...
}

-- TAG-DMRS-UPLINKCONFIG-STOP
-- TAG-DOWNLINKCONFIGCOMMON-START
DownlinkConfigCommon ::= SEQUENCE {
   frequencyInfoDL [0] FrequencyInfoDL OPTIONAL, -- Cond InterFreqHOAndServCellAdd
   initialDownlinkBWP [1] BWP-DownlinkCommon OPTIONAL,
   ...,
   [[
      initialDownlinkBWP-RedCap-r17 [2] BWP-DownlinkCommon OPTIONAL
   ]]
}

-- TAG-FREQUENCYINFODL-SIB-STOP
-- TAG-FREQUENCYINFOUL-START
FrequencyInfoUL ::= SEQUENCE {
   frequencyBandList [0] MultiFrequencyBandListNR OPTIONAL, -- Cond FDD-OrSUL
   absoluteFrequencyPointA [1] ARFCN-ValueNR OPTIONAL, -- Cond FDD-OrSUL
   scs-SpecificCarrierList [2] SEQUENCE (SIZE (1..maxSCSs)) OF SCS-SpecificCarrier,
   additionalSpectrumEmission [3] AdditionalSpectrumEmission OPTIONAL, -- Need S
   p-Max [4] P-Max OPTIONAL, -- Need S
   frequencyShift7p5khz [5] ENUMERATED { true(0) } OPTIONAL,
   ...,
   [[
      additionalSpectrumEmission-v1760 [6] AdditionalSpectrumEmission-v1760
          OPTIONAL
   ]]
}

-- TAG-UPLINKCANCELLATION-STOP
-- TAG-UPLINKCONFIGCOMMON-START
UplinkConfigCommon ::= SEQUENCE {
   frequencyInfoUL [0] FrequencyInfoUL OPTIONAL, -- Cond InterFreqHOAndServCellAdd
   initialUplinkBWP [1] BWP-UplinkCommon OPTIONAL, -- Cond ServCellAdd
   dummy [2] TimeAlignmentTimer
}

HighSpeedConfig-v1700 ::= SEQUENCE {
   highSpeedMeasCA-Scell-r17 [0] ENUMERATED { true(0) } OPTIONAL, -- Cond SCellOnly
   highSpeedMeasInterFreq-r17 [1] ENUMERATED { true(0) } OPTIONAL, -- Cond SpCellOnly2
   highSpeedDemodCA-Scell-r17 [2] ENUMERATED { true(0) } OPTIONAL,
   ...
}

UplinkConfigCommon-v1700 ::= SEQUENCE {
   initialUplinkBWP-RedCap-r17 [0] BWP-UplinkCommon OPTIONAL -- Need R
}

-- TAG-SERVINGCELLCONFIG-STOP
-- TAG-SERVINGCELLCONFIGCOMMON-START
ServingCellConfigCommon ::= SEQUENCE {
   physCellId [0] PhysCellId OPTIONAL, -- Cond HOAndServCellAdd,
   downlinkConfigCommon [1] DownlinkConfigCommon OPTIONAL, -- Cond HOAndServCellAdd
   uplinkConfigCommon [2] UplinkConfigCommon OPTIONAL, -- Need M
   supplementaryUplinkConfig [3] UplinkConfigCommon OPTIONAL, -- Need S
   n-TimingAdvanceOffset [4] ENUMERATED { n0(0), n25600(1), n39936(2) }
       OPTIONAL, -- Need S
   ssb-PositionsInBurst [5] EXPLICIT CHOICE {
      shortBitmap [0] BIT STRING  (SIZE (4)),
      mediumBitmap [1] BIT STRING  (SIZE (8)),
      longBitmap [2] BIT STRING  (SIZE (64))
   } OPTIONAL, -- Cond AbsFreqSSB
   ssb-periodicityServingCell [6] ENUMERATED { ms5(0), ms10(1), ms20(2), 
      ms40(3), ms80(4), ms160(5), spare2(6), spare1(7) } OPTIONAL, -- Need S
   dmrs-TypeA-Position [7] ENUMERATED { pos2(0), pos3(1) },
   lte-CRS-ToMatchAround [8] EXPLICIT CHOICE {
      release [0] NULL,
      setup [1] EXPLICIT RateMatchPatternLTE-CRS
   } OPTIONAL, -- Need M
   rateMatchPatternToAddModList [9] SEQUENCE (SIZE (1..maxNrofRateMatchPatterns)) OF RateMatchPattern
       OPTIONAL, -- Need N
   rateMatchPatternToReleaseList [10] SEQUENCE (SIZE (1..maxNrofRateMatchPatterns)) OF 
      RateMatchPatternId OPTIONAL, -- Need N
   ssbSubcarrierSpacing [11] SubcarrierSpacing OPTIONAL, -- Cond HOAndServCellWithSSB
   tdd-UL-DL-ConfigurationCommon [12] TDD-UL-DL-ConfigCommon OPTIONAL, -- Cond TDD
   ss-PBCH-BlockPower [13] INTEGER (-60..50),
   ...,
   [[
      channelAccessMode-r16 [14] EXPLICIT CHOICE {
         dynamic [0] NULL,
         semiStatic [1] SemiStaticChannelAccessConfig-r16
      } OPTIONAL,
      discoveryBurstWindowLength-r16 [15] ENUMERATED { ms0dot5(0), ms1(1), 
         ms2(2), ms3(3), ms4(4), ms5(5) } OPTIONAL,
      ssb-PositionQCL-r16 [16] SSB-PositionQCL-Relation-r16 OPTIONAL,
      highSpeedConfig-r16 [17] HighSpeedConfig-r16 OPTIONAL
   ]],
   [[
      highSpeedConfig-v1700 [18] HighSpeedConfig-v1700 OPTIONAL,
      channelAccessMode2-r17 [19] ENUMERATED { enabled(0) } OPTIONAL,
      discoveryBurstWindowLength-r17 [20] ENUMERATED { ms0dot125(0), 
         ms0dot25(1), ms0dot5(2), ms0dot75(3), ms1(4), ms1dot25(5) } OPTIONAL,
      ssb-PositionQCL-r17 [21] SSB-PositionQCL-Relation-r17 OPTIONAL,
      highSpeedConfigFR2-r17 [22] HighSpeedConfigFR2-r17 OPTIONAL,
      uplinkConfigCommon-v1700 [23] UplinkConfigCommon-v1700 OPTIONAL,
      ntn-Config-r17 [24] NTN-Config-r17 OPTIONAL
   ]],
   [[
      featurePriorities-r17 [25] SEQUENCE {
         redCapPriority-r17 [0] FeaturePriority-r17 OPTIONAL, -- Need R
         slicingPriority-r17 [1] FeaturePriority-r17 OPTIONAL, -- Need R
         msg3-Repetitions-Priority-r17 [2] FeaturePriority-r17 OPTIONAL, -- Need R
         sdt-Priority-r17 [3] FeaturePriority-r17 OPTIONAL -- Need R
      } OPTIONAL
   ]],
   [[
      ra-ChannelAccess-r17 [26] ENUMERATED { enabled(0) } OPTIONAL
   ]]
}

CFRA-SSB-Resource ::= SEQUENCE {
   ssb [0] SSB-Index,
   ra-PreambleIndex [1] INTEGER (0..63),
   ...,
   [[
      msgA-PUSCH-Resource-Index-r16 [2] INTEGER (0..3071) OPTIONAL
   ]]
}

CFRA-CSIRS-Resource ::= SEQUENCE {
   csi-RS [0] CSI-RS-Index,
   ra-OccasionList [1] SEQUENCE (SIZE (1..maxRA-OccasionsPerCSIRS)) OF INTEGER (0..maxRA-Occasions-1),
   ra-PreambleIndex [2] INTEGER (0..63),
   ...
}

CFRA ::= SEQUENCE {
   occasions [0] SEQUENCE {
      rach-ConfigGeneric [0] RACH-ConfigGeneric,
      ssb-perRACH-Occasion [1] ENUMERATED { oneEighth(0), oneFourth(1), 
         oneHalf(2), one(3), two(4), four(5), eight(6), sixteen(7) } OPTIONAL
                                                                                                                        -- Cond Mandatory
   } OPTIONAL, -- Need S
   resources [1] EXPLICIT CHOICE {
      ssb [0] SEQUENCE {
         ssb-ResourceList [0] SEQUENCE (SIZE (1..maxRA-SSB-Resources)) OF CFRA-SSB-Resource,
         ra-ssb-OccasionMaskIndex [1] INTEGER (0..15)
      },
      csirs [1] SEQUENCE {
         csirs-ResourceList [0] SEQUENCE (SIZE (1..maxRA-CSIRS-Resources)) OF CFRA-CSIRS-Resource,
         rsrp-ThresholdCSI-RS [1] RSRP-Range
      }
   },
   ...,
   [[
      totalNumberOfRA-Preambles [2] INTEGER (1..63) OPTIONAL
   ]]
}

CFRA-TwoStep-r16 ::= SEQUENCE {
   occasionsTwoStepRA-r16 [0] SEQUENCE {
      rach-ConfigGenericTwoStepRA-r16 [0] RACH-ConfigGenericTwoStepRA-r16,
      ssb-PerRACH-OccasionTwoStepRA-r16 [1] ENUMERATED { oneEighth(0), 
         oneFourth(1), oneHalf(2), one(3), two(4), four(5), eight(6), 
         sixteen(7) }
   } OPTIONAL, -- Need S
   msgA-CFRA-PUSCH-r16 [1] MsgA-PUSCH-Resource-r16,
   msgA-TransMax-r16 [2] ENUMERATED { n1(0), n2(1), n4(2), n6(3), n8(4), n10(5)
      , n20(6), n50(7), n100(8), n200(9) } OPTIONAL, -- Need S
   resourcesTwoStep-r16 [3] SEQUENCE {
      ssb-ResourceList [0] SEQUENCE (SIZE (1..maxRA-SSB-Resources)) OF CFRA-SSB-Resource,
      ra-ssb-OccasionMaskIndex [1] INTEGER (0..15)
   },
   ...
}

-- TAG-RACH-CONFIGCOMMONTWOSTEPRA-STOP
-- TAG-RACH-CONFIGDEDICATED-START
RACH-ConfigDedicated ::= SEQUENCE {
   cfra [0] CFRA OPTIONAL, -- Need S
   ra-Prioritization [1] RA-Prioritization OPTIONAL,
   ...,
   [[
      ra-PrioritizationTwoStep-r16 [2] RA-Prioritization OPTIONAL,
      cfra-TwoStep-r16 [3] CFRA-TwoStep-r16 OPTIONAL
   ]]
}

DAPS-UplinkPowerConfig-r16 ::= SEQUENCE {
   p-DAPS-Source-r16 [0] P-Max,
   p-DAPS-Target-r16 [1] P-Max,
   uplinkPowerSharingDAPS-Mode-r16 [2] ENUMERATED { semi-static-mode1(0), 
      semi-static-mode2(1), dynamic(2) }
}

SL-PathSwitchConfig-r17 ::= SEQUENCE {
   targetRelayUE-Identity-r17 [0] SL-SourceIdentity-r17,
   t420-r17 [1] ENUMERATED { ms50(0), ms100(1), ms150(2), ms200(3), ms500(4), 
      ms1000(5), ms2000(6), ms10000(7) },
   ...
}

ReconfigurationWithSync ::= SEQUENCE {
   spCellConfigCommon [0] ServingCellConfigCommon OPTIONAL, -- Need M
   newUE-Identity [1] RNTI-Value,
   t304 [2] ENUMERATED { ms50(0), ms100(1), ms150(2), ms200(3), ms500(4), 
      ms1000(5), ms2000(6), ms10000(7) },
   rach-ConfigDedicated [3] EXPLICIT CHOICE {
      uplink [0] RACH-ConfigDedicated,
      supplementaryUplink [1] RACH-ConfigDedicated
   } OPTIONAL,
   ...,
   [[
      smtc [4] SSB-MTC OPTIONAL
   ]],
   [[
      daps-UplinkPowerConfig-r16 [5] DAPS-UplinkPowerConfig-r16 OPTIONAL
   ]],
   [[
      sl-PathSwitchConfig-r17 [6] SL-PathSwitchConfig-r17 OPTIONAL
   ]]
}

-- TAG-RLC-CONFIG-STOP
-- TAG-RLF-TIMERSANDCONSTANTS-START
RLF-TimersAndConstants ::= SEQUENCE {
   t310 [0] ENUMERATED { ms0(0), ms50(1), ms100(2), ms200(3), ms500(4), 
      ms1000(5), ms2000(6), ms4000(7), ms6000(8) },
   n310 [1] ENUMERATED { n1(0), n2(1), n3(2), n4(3), n6(4), n8(5), n10(6), 
      n20(7) },
   n311 [2] ENUMERATED { n1(0), n2(1), n3(2), n4(3), n5(4), n6(5), n8(6), 
      n10(7) },
   ...,
   [[
      t311 [3] ENUMERATED { ms1000(0), ms3000(1), ms5000(2), ms10000(3), 
         ms15000(4), ms20000(5), ms30000(6) }
   ]]
}

TDD-UL-DL-SlotConfig ::= SEQUENCE {
   slotIndex [0] TDD-UL-DL-SlotIndex,
   symbols [1] EXPLICIT CHOICE {
      allDownlink [0] NULL,
      allUplink [1] NULL,
      explicit [2] SEQUENCE {
         nrofDownlinkSymbols [0] INTEGER (1..maxNrofSymbols-1) OPTIONAL, -- Need S
         nrofUplinkSymbols [1] INTEGER (1..maxNrofSymbols-1) OPTIONAL -- Need S
      }
   }
}

-- TAG-TDD-UL-DL-CONFIGCOMMON-STOP
-- TAG-TDD-UL-DL-CONFIGDEDICATED-START
TDD-UL-DL-ConfigDedicated ::= SEQUENCE {
   slotSpecificConfigurationsToAddModList [0] SEQUENCE (SIZE (1..maxNrofSlots)) OF 
      TDD-UL-DL-SlotConfig OPTIONAL, -- Need N
   slotSpecificConfigurationsToReleaseList [1] SEQUENCE (SIZE (1..maxNrofSlots)) OF 
      TDD-UL-DL-SlotIndex OPTIONAL,
   ...
}

-- TAG-SPEEDSTATESCALEFACTORS-STOP
-- TAG-SPS-CONFIG-START
SPS-Config ::= SEQUENCE {
   periodicity [0] ENUMERATED { ms10(0), ms20(1), ms32(2), ms40(3), ms64(4), 
      ms80(5), ms128(6), ms160(7), ms320(8), ms640(9), spare6(10), spare5(11), 
      spare4(12), spare3(13), spare2(14), spare1(15) },
   nrofHARQ-Processes [1] INTEGER (1..8),
   n1PUCCH-AN [2] PUCCH-ResourceId OPTIONAL, -- Need M
   mcs-Table [3] ENUMERATED { qam64LowSE(0) } OPTIONAL,
   ...,
   [[
      sps-ConfigIndex-r16 [4] SPS-ConfigIndex-r16 OPTIONAL,
      harq-ProcID-Offset-r16 [5] INTEGER (0..15) OPTIONAL,
      periodicityExt-r16 [6] INTEGER (1..5120) OPTIONAL,
      harq-CodebookID-r16 [7] INTEGER (1..2) OPTIONAL,
      pdsch-AggregationFactor-r16 [8] ENUMERATED { n1(0), n2(1), n4(2), n8(3) }
          OPTIONAL
   ]],
   [[
      sps-HARQ-Deferral-r17 [9] INTEGER (1..32) OPTIONAL,
      n1PUCCH-AN-PUCCHsSCell-r17 [10] PUCCH-ResourceId OPTIONAL,
      periodicityExt-r17 [11] INTEGER (1..40960) OPTIONAL,
      nrofHARQ-Processes-v1710 [12] INTEGER (9..32) OPTIONAL,
      harq-ProcID-Offset-v1700 [13] INTEGER (16..31) OPTIONAL
   ]]
}

RadioLinkMonitoringRS ::= SEQUENCE {
   radioLinkMonitoringRS-Id [0] RadioLinkMonitoringRS-Id,
   purpose [1] ENUMERATED { beamFailure(0), rlf(1), both(2) },
   detectionResource [2] EXPLICIT CHOICE {
      ssb-Index [0] SSB-Index,
      csi-RS-Index [1] NZP-CSI-RS-ResourceId
   },
   ...
}

BeamLinkMonitoringRS-r17 ::= SEQUENCE {
   beamLinkMonitoringRS-Id-r17 [0] BeamLinkMonitoringRS-Id-r17,
   detectionResource-r17 [1] EXPLICIT CHOICE {
      ssb-Index [0] SSB-Index,
      csi-RS-Index [1] NZP-CSI-RS-ResourceId
   },
   ...
}

BeamFailureDetectionSet-r17 ::= SEQUENCE {
   bfdResourcesToAddModList-r17 [0] SEQUENCE (SIZE (1..maxNrofBFDResourcePerSet-r17)) OF 
      BeamLinkMonitoringRS-r17 OPTIONAL,
                                                                                                                             -- Need N
   bfdResourcesToReleaseList-r17 [1] SEQUENCE (SIZE (1..maxNrofBFDResourcePerSet-r17)) OF 
      BeamLinkMonitoringRS-Id-r17 OPTIONAL,
                                                                                                                             -- Need N
   beamFailureInstanceMaxCount-r17 [2] ENUMERATED { n1(0), n2(1), n3(2), n4(3)
      , n5(4), n6(5), n8(6), n10(7) } OPTIONAL, -- Need R
   beamFailureDetectionTimer-r17 [3] ENUMERATED { pbfd1(0), pbfd2(1), pbfd3(2)
      , pbfd4(3), pbfd5(4), pbfd6(5), pbfd8(6), pbfd10(7) } OPTIONAL,
   ...
}

BeamFailureDetection-r17 ::= SEQUENCE {
   failureDetectionSet1-r17 [0] BeamFailureDetectionSet-r17 OPTIONAL, -- Need R
   failureDetectionSet2-r17 [1] BeamFailureDetectionSet-r17 OPTIONAL, -- Need R
   additionalPCI-r17 [2] AdditionalPCIIndex-r17 OPTIONAL -- Need R
}

-- TAG-RADIOBEARERCONFIG-STOP
-- TAG-RADIOLINKMONITORINGCONFIG-START
RadioLinkMonitoringConfig ::= SEQUENCE {
   failureDetectionResourcesToAddModList [0] SEQUENCE (SIZE (1..maxNrofFailureDetectionResources)) OF 
      RadioLinkMonitoringRS OPTIONAL,
                                                                                                                             -- Need N
   failureDetectionResourcesToReleaseList [1] SEQUENCE (SIZE (1..maxNrofFailureDetectionResources)) OF 
      RadioLinkMonitoringRS-Id OPTIONAL,
                                                                                                                             -- Need N
   beamFailureInstanceMaxCount [2] ENUMERATED { n1(0), n2(1), n3(2), n4(3), 
      n5(4), n6(5), n8(6), n10(7) } OPTIONAL, -- Need R
   beamFailureDetectionTimer [3] ENUMERATED { pbfd1(0), pbfd2(1), pbfd3(2), 
      pbfd4(3), pbfd5(4), pbfd6(5), pbfd8(6), pbfd10(7) } OPTIONAL,
   ...,
   [[
      beamFailure-r17 [4] BeamFailureDetection-r17 OPTIONAL
   ]]
}

SPS-ConfigToAddModList-r16 ::= SEQUENCE (SIZE (1..maxNrofSPS-Config-r16)) OF SPS-Config

SPS-ConfigToReleaseList-r16 ::= SEQUENCE (SIZE (1..maxNrofSPS-Config-r16)) OF SPS-ConfigIndex-r16

SPS-ConfigDeactivationState-r16 ::= SEQUENCE (SIZE (1..maxNrofSPS-Config-r16)) OF SPS-ConfigIndex-r16
   

SPS-ConfigDeactivationStateList-r16 ::= SEQUENCE (SIZE (1..maxNrofSPS-DeactivationState)) OF 
   SPS-ConfigDeactivationState-r16

-- TAG-BWP-UPLINKDEDICATED-STOP
-- TAG-CANDIDATEBEAMRS-START
CandidateBeamRS-r16 ::= SEQUENCE {
   candidateBeamConfig-r16 [0] EXPLICIT CHOICE {
      ssb-r16 [0] SSB-Index,
      csi-RS-r16 [1] NZP-CSI-RS-ResourceId
   },
   servingCellId [1] ServCellIndex OPTIONAL -- Need R
}

-- TAG-BEAMFAILURERECOVERYCONFIG-STOP
-- TAG-BEAMFAILURERECOVERYRSCONFIG-START
BeamFailureRecoveryRSConfig-r16 ::= SEQUENCE {
   rsrp-ThresholdBFR-r16 [0] RSRP-Range OPTIONAL, -- Need M
   candidateBeamRS-List-r16 [1] SEQUENCE (SIZE (1..maxNrofCandidateBeams-r16)) OF CandidateBeamRS-r16
       OPTIONAL,
   ...,
   [[
      candidateBeamRS-List2-r17 [2] SEQUENCE (SIZE (1..maxNrofCandidateBeams-r16)) OF CandidateBeamRS-r16
          OPTIONAL
   ]]
}

SPS-ConfigMulticastToAddModList-r17 ::= SEQUENCE (SIZE (1..8)) OF SPS-Config

SPS-ConfigMulticastToReleaseList-r17 ::= SEQUENCE (SIZE (1..8)) OF 
   SPS-ConfigIndex-r16

-- TAG-CELLRESELECTIONSUBPRIORITY-STOP
-- TAG-CFR-CONFIGMULTICAST-START
CFR-ConfigMulticast-r17 ::= SEQUENCE {
   locationAndBandwidthMulticast-r17 [0] INTEGER (0..37949) OPTIONAL, -- Need S
   pdcch-ConfigMulticast-r17 [1] PDCCH-Config OPTIONAL, -- Need M
   pdsch-ConfigMulticast-r17 [2] PDSCH-Config OPTIONAL, -- Need M
   sps-ConfigMulticastToAddModList-r17 [3] SPS-ConfigMulticastToAddModList-r17
       OPTIONAL, -- Need N
   sps-ConfigMulticastToReleaseList-r17 [4] 
      SPS-ConfigMulticastToReleaseList-r17 OPTIONAL -- Need N
}

DL-PPW-PeriodicityAndStartSlot-r17 ::= CHOICE {
   scs15 [0] EXPLICIT CHOICE {
      n4 [0] INTEGER (0..3),
      n5 [1] INTEGER (0..4),
      n8 [2] INTEGER (0..7),
      n10 [3] INTEGER (0..9),
      n16 [4] INTEGER (0..15),
      n20 [5] INTEGER (0..19),
      n32 [6] INTEGER (0..31),
      n40 [7] INTEGER (0..39),
      n64 [8] INTEGER (0..63),
      n80 [9] INTEGER (0..79),
      n160 [10] INTEGER (0..159),
      n320 [11] INTEGER (0..319),
      n640 [12] INTEGER (0..639),
      n1280 [13] INTEGER (0..1279),
      n2560 [14] INTEGER (0..2559),
      n5120 [15] INTEGER (0..5119),
      n10240 [16] INTEGER (0..10239),
      ...
   },
   scs30 [1] EXPLICIT CHOICE {
      n8 [0] INTEGER (0..7),
      n10 [1] INTEGER (0..9),
      n16 [2] INTEGER (0..15),
      n20 [3] INTEGER (0..19),
      n32 [4] INTEGER (0..31),
      n40 [5] INTEGER (0..39),
      n64 [6] INTEGER (0..63),
      n80 [7] INTEGER (0..79),
      n128 [8] INTEGER (0..127),
      n160 [9] INTEGER (0..159),
      n320 [10] INTEGER (0..319),
      n640 [11] INTEGER (0..639),
      n1280 [12] INTEGER (0..1279),
      n2560 [13] INTEGER (0..2559),
      n5120 [14] INTEGER (0..5119),
      n10240 [15] INTEGER (0..10239),
      n20480 [16] INTEGER (0..20479),
      ...
   },
   scs60 [2] EXPLICIT CHOICE {
      n16 [0] INTEGER (0..15),
      n20 [1] INTEGER (0..19),
      n32 [2] INTEGER (0..31),
      n40 [3] INTEGER (0..39),
      n64 [4] INTEGER (0..63),
      n80 [5] INTEGER (0..79),
      n128 [6] INTEGER (0..127),
      n160 [7] INTEGER (0..159),
      n256 [8] INTEGER (0..255),
      n320 [9] INTEGER (0..319),
      n640 [10] INTEGER (0..639),
      n1280 [11] INTEGER (0..1279),
      n2560 [12] INTEGER (0..2559),
      n5120 [13] INTEGER (0..5119),
      n10240 [14] INTEGER (0..10239),
      n20480 [15] INTEGER (0..20479),
      n40960 [16] INTEGER (0..40959),
      ...
   },
   scs120 [3] EXPLICIT CHOICE {
      n32 [0] INTEGER (0..31),
      n40 [1] INTEGER (0..39),
      n64 [2] INTEGER (0..63),
      n80 [3] INTEGER (0..79),
      n128 [4] INTEGER (0..127),
      n160 [5] INTEGER (0..159),
      n256 [6] INTEGER (0..255),
      n320 [7] INTEGER (0..319),
      n512 [8] INTEGER (0..511),
      n640 [9] INTEGER (0..639),
      n1280 [10] INTEGER (0..1279),
      n2560 [11] INTEGER (0..2559),
      n5120 [12] INTEGER (0..5119),
      n10240 [13] INTEGER (0..10239),
      n20480 [14] INTEGER (0..20479),
      n40960 [15] INTEGER (0..40959),
      n81920 [16] INTEGER (0..81919),
      ...
   },
   ...
}

-- TAG-DEDICATED-NAS-MESSAGE-STOP
-- TAG-DL-PPW-PRECONFIG-START
DL-PPW-PreConfig-r17 ::= SEQUENCE {
   dl-PPW-ID-r17 [0] DL-PPW-ID-r17,
   dl-PPW-PeriodicityAndStartSlot-r17 [1] EXPLICIT 
      DL-PPW-PeriodicityAndStartSlot-r17,
   length-r17 [2] INTEGER (1..160),
   type-r17 [3] ENUMERATED { type1A(0), type1B(1), type2(2) } OPTIONAL, -- Cond MultiType
   priority-r17 [4] ENUMERATED { st1(0), st2(1), st3(2) } OPTIONAL -- Cond MultiState
}

DL-PPW-PreConfigToAddModList-r17 ::= SEQUENCE (SIZE (1..maxNrofPPW-Config-r17)) OF 
   DL-PPW-PreConfig-r17

DL-PPW-PreConfigToReleaseList-r17 ::= SEQUENCE (SIZE (1..maxNrofPPW-Config-r17)) OF DL-PPW-ID-r17

-- TAG-NG-5G-S-TMSI-STOP
-- TAG-NONCELLDEFININGSSB-START
NonCellDefiningSSB-r17 ::= SEQUENCE {
   absoluteFrequencySSB-r17 [0] ARFCN-ValueNR,
   ssb-Periodicity-r17 [1] ENUMERATED { ms5(0), ms10(1), ms20(2), ms40(3), 
      ms80(4), ms160(5), spare2(6), spare1(7) } OPTIONAL, -- Need S
   ssb-TimeOffset-r17 [2] ENUMERATED { ms5(0), ms10(1), ms15(2), ms20(3), 
      ms40(4), ms80(5), spare2(6), spare1(7) } OPTIONAL,
   ...
}

-- TAG-BWP-DOWNLINKCOMMON-STOP
-- TAG-BWP-DOWNLINKDEDICATED-START
BWP-DownlinkDedicated ::= SEQUENCE {
   pdcch-Config [0] EXPLICIT CHOICE {
      release [0] NULL,
      setup [1] EXPLICIT PDCCH-Config
   } OPTIONAL, -- Need M
   pdsch-Config [1] EXPLICIT CHOICE {
      release [0] NULL,
      setup [1] EXPLICIT PDSCH-Config
   } OPTIONAL, -- Need M
   sps-Config [2] EXPLICIT CHOICE {
      release [0] NULL,
      setup [1] EXPLICIT SPS-Config
   } OPTIONAL, -- Need M
   radioLinkMonitoringConfig [3] EXPLICIT CHOICE {
      release [0] NULL,
      setup [1] EXPLICIT RadioLinkMonitoringConfig
   } OPTIONAL,
   ...,
   [[
      sps-ConfigToAddModList-r16 [4] SPS-ConfigToAddModList-r16 OPTIONAL,
      sps-ConfigToReleaseList-r16 [5] SPS-ConfigToReleaseList-r16 OPTIONAL,
      sps-ConfigDeactivationStateList-r16 [6] 
         SPS-ConfigDeactivationStateList-r16 OPTIONAL,
      beamFailureRecoverySCellConfig-r16 [7] EXPLICIT CHOICE {
         release [0] NULL,
         setup [1] EXPLICIT BeamFailureRecoveryRSConfig-r16
      } OPTIONAL,
      sl-PDCCH-Config-r16 [8] EXPLICIT CHOICE {
         release [0] NULL,
         setup [1] EXPLICIT PDCCH-Config
      } OPTIONAL,
      sl-V2X-PDCCH-Config-r16 [9] EXPLICIT CHOICE {
         release [0] NULL,
         setup [1] EXPLICIT PDCCH-Config
      } OPTIONAL
   ]],
   [[
      preConfGapStatus-r17 [10] BIT STRING  (SIZE (maxNrofGapId-r17)) OPTIONAL,
      beamFailureRecoverySpCellConfig-r17 [11] EXPLICIT CHOICE {
         release [0] NULL,
         setup [1] EXPLICIT BeamFailureRecoveryRSConfig-r16
      } OPTIONAL,
      harq-FeedbackEnablingforSPSactive-r17 [12] BOOLEAN OPTIONAL,
      cfr-ConfigMulticast-r17 [13] EXPLICIT CHOICE {
         release [0] NULL,
         setup [1] EXPLICIT CFR-ConfigMulticast-r17
      } OPTIONAL,
      dl-PPW-PreConfigToAddModList-r17 [14] DL-PPW-PreConfigToAddModList-r17
          OPTIONAL,
      dl-PPW-PreConfigToReleaseList-r17 [15] DL-PPW-PreConfigToReleaseList-r17
          OPTIONAL,
      nonCellDefiningSSB-r17 [16] NonCellDefiningSSB-r17 OPTIONAL,
      servingCellMO-r17 [17] MeasObjectId OPTIONAL
   ]]
}

-- TAG-BWP-STOP
-- TAG-BWP-DOWNLINK-START
BWP-Downlink ::= SEQUENCE {
   bwp-Id [0] BWP-Id,
   bwp-Common [1] BWP-DownlinkCommon OPTIONAL, -- Cond SetupOtherBWP
   bwp-Dedicated [2] BWP-DownlinkDedicated OPTIONAL,
   ...
}

-- A set with one or more PUCCH resources
PUCCH-ResourceSet ::= SEQUENCE {
   pucch-ResourceSetId [0] PUCCH-ResourceSetId,
   resourceList [1] SEQUENCE (SIZE (1..maxNrofPUCCH-ResourcesPerSet)) OF PUCCH-ResourceId,
   maxPayloadSize [2] INTEGER (4..256) OPTIONAL -- Need R
}

PUCCH-format0 ::= SEQUENCE {
   initialCyclicShift [0] INTEGER (0..11),
   nrofSymbols [1] INTEGER (1..2),
   startingSymbolIndex [2] INTEGER (0..13)
}

PUCCH-format1 ::= SEQUENCE {
   initialCyclicShift [0] INTEGER (0..11),
   nrofSymbols [1] INTEGER (4..14),
   startingSymbolIndex [2] INTEGER (0..10),
   timeDomainOCC [3] INTEGER (0..6)
}

PUCCH-format2 ::= SEQUENCE {
   nrofPRBs [0] INTEGER (1..16),
   nrofSymbols [1] INTEGER (1..2),
   startingSymbolIndex [2] INTEGER (0..13)
}

PUCCH-format3 ::= SEQUENCE {
   nrofPRBs [0] INTEGER (1..16),
   nrofSymbols [1] INTEGER (4..14),
   startingSymbolIndex [2] INTEGER (0..10)
}

PUCCH-format4 ::= SEQUENCE {
   nrofSymbols [0] INTEGER (4..14),
   occ-Length [1] ENUMERATED { n2(0), n4(1) },
   occ-Index [2] ENUMERATED { n0(0), n1(1), n2(2), n3(3) },
   startingSymbolIndex [3] INTEGER (0..10)
}

PUCCH-Resource ::= SEQUENCE {
   pucch-ResourceId [0] PUCCH-ResourceId,
   startingPRB [1] PRB-Id,
   intraSlotFrequencyHopping [2] ENUMERATED { enabled(0) } OPTIONAL, -- Need R
   secondHopPRB [3] PRB-Id OPTIONAL, -- Need R
   format [4] EXPLICIT CHOICE {
      format0 [0] PUCCH-format0,
      format1 [1] PUCCH-format1,
      format2 [2] PUCCH-format2,
      format3 [3] PUCCH-format3,
      format4 [4] PUCCH-format4
   }
}

PUCCH-FormatConfig ::= SEQUENCE {
   interslotFrequencyHopping [0] ENUMERATED { enabled(0) } OPTIONAL, -- Need R
   additionalDMRS [1] ENUMERATED { true(0) } OPTIONAL, -- Need R
   maxCodeRate [2] PUCCH-MaxCodeRate OPTIONAL, -- Need R
   nrofSlots [3] ENUMERATED { n2(0), n4(1), n8(2) } OPTIONAL, -- Need S
   pi2BPSK [4] ENUMERATED { enabled(0) } OPTIONAL, -- Need R
   simultaneousHARQ-ACK-CSI [5] ENUMERATED { true(0) } OPTIONAL -- Need R
}

-- TAG-SCHEDULINGREQUESTID-STOP
-- TAG-SCHEDULINGREQUESTRESOURCECONFIG-START
SchedulingRequestResourceConfig ::= SEQUENCE {
   schedulingRequestResourceId [0] SchedulingRequestResourceId,
   schedulingRequestID [1] SchedulingRequestId,
   periodicityAndOffset [2] EXPLICIT CHOICE {
      sym2 [0] NULL,
      sym6or7 [1] NULL,
      sl1 [2] NULL, -- Recurs in every slot
      sl2 [3] INTEGER (0..1),
      sl4 [4] INTEGER (0..3),
      sl5 [5] INTEGER (0..4),
      sl8 [6] INTEGER (0..7),
      sl10 [7] INTEGER (0..9),
      sl16 [8] INTEGER (0..15),
      sl20 [9] INTEGER (0..19),
      sl40 [10] INTEGER (0..39),
      sl80 [11] INTEGER (0..79),
      sl160 [12] INTEGER (0..159),
      sl320 [13] INTEGER (0..319),
      sl640 [14] INTEGER (0..639)
   } OPTIONAL, -- Need M
   resource [3] PUCCH-ResourceId OPTIONAL -- Need M
}

PUCCH-SRS ::= SEQUENCE {
   resource [0] SRS-ResourceId,
   uplinkBWP [1] BWP-Id
}

-- TAG-PUCCH-POWERCONTROL-STOP
-- TAG-PUCCH-SPATIALRELATIONINFO-START
PUCCH-SpatialRelationInfo ::= SEQUENCE {
   pucch-SpatialRelationInfoId [0] PUCCH-SpatialRelationInfoId,
   servingCellId [1] ServCellIndex OPTIONAL, -- Need S
   referenceSignal [2] EXPLICIT CHOICE {
      ssb-Index [0] SSB-Index,
      csi-RS-Index [1] NZP-CSI-RS-ResourceId,
      srs [2] PUCCH-SRS
   },
   pucch-PathlossReferenceRS-Id [3] PUCCH-PathlossReferenceRS-Id,
   p0-PUCCH-Id [4] P0-PUCCH-Id,
   closedLoopIndex [5] ENUMERATED { i0(0), i1(1) }
}

P0-PUCCH ::= SEQUENCE {
   p0-PUCCH-Id [0] P0-PUCCH-Id,
   p0-PUCCH-Value [1] INTEGER (-16..15)
}

PUCCH-PathlossReferenceRS ::= SEQUENCE {
   pucch-PathlossReferenceRS-Id [0] PUCCH-PathlossReferenceRS-Id,
   referenceSignal [1] EXPLICIT CHOICE {
      ssb-Index [0] SSB-Index,
      csi-RS-Index [1] NZP-CSI-RS-ResourceId
   }
}

PUCCH-PathlossReferenceRS-r16 ::= SEQUENCE {
   pucch-PathlossReferenceRS-Id-r16 [0] PUCCH-PathlossReferenceRS-Id-v1610,
   referenceSignal-r16 [1] EXPLICIT CHOICE {
      ssb-Index-r16 [0] SSB-Index,
      csi-RS-Index-r16 [1] NZP-CSI-RS-ResourceId
   }
}

PathlossReferenceRSs-v1610 ::= SEQUENCE (SIZE (1..maxNrofPUCCH-PathlossReferenceRSsDiff-r16)) OF 
   PUCCH-PathlossReferenceRS-r16

-- TAG-PUCCH-PATHLOSSREFERENCERS-ID-STOP
-- TAG-PUCCH-POWERCONTROL-START
PUCCH-PowerControl ::= SEQUENCE {
   deltaF-PUCCH-f0 [0] INTEGER (-16..15) OPTIONAL, -- Need R
   deltaF-PUCCH-f1 [1] INTEGER (-16..15) OPTIONAL, -- Need R
   deltaF-PUCCH-f2 [2] INTEGER (-16..15) OPTIONAL, -- Need R
   deltaF-PUCCH-f3 [3] INTEGER (-16..15) OPTIONAL, -- Need R
   deltaF-PUCCH-f4 [4] INTEGER (-16..15) OPTIONAL, -- Need R
   p0-Set [5] SEQUENCE (SIZE (1..maxNrofPUCCH-P0-PerSet)) OF P0-PUCCH OPTIONAL, -- Need M
   pathlossReferenceRSs [6] SEQUENCE (SIZE (1..maxNrofPUCCH-PathlossReferenceRSs)) OF PUCCH-PathlossReferenceRS
       OPTIONAL,
                                                                                                                           -- Need M
   twoPUCCH-PC-AdjustmentStates [7] ENUMERATED { twoStates(0) } OPTIONAL,
   ...,
   [[
      pathlossReferenceRSs-v1610 [8] EXPLICIT CHOICE {
         release [0] NULL,
         setup [1] EXPLICIT PathlossReferenceRSs-v1610
      } OPTIONAL
   ]]
}

PUCCH-ResourceExt-v1610 ::= SEQUENCE {
   interlaceAllocation-r16 [0] SEQUENCE {
      rb-SetIndex-r16 [0] INTEGER (0..4),
      interlace0-r16 [1] EXPLICIT CHOICE {
         scs15 [0] INTEGER (0..9),
         scs30 [1] INTEGER (0..4)
      }
   } OPTIONAL, --Need R
   format-v1610 [1] EXPLICIT CHOICE {
      interlace1-v1610 [0] INTEGER (0..9),
      occ-v1610 [1] SEQUENCE {
         occ-Length-v1610 [0] ENUMERATED { n2(0), n4(1) } OPTIONAL, -- Need M
         occ-Index-v1610 [1] ENUMERATED { n0(0), n1(1), n2(2), n3(3) } OPTIONAL
             -- Need M
      }
   } OPTIONAL,
   ...,
   [[
      format-v1700 [2] SEQUENCE {
         nrofPRBs-r17 [0] INTEGER (1..16)
      } OPTIONAL,
      pucch-RepetitionNrofSlots-r17 [3] ENUMERATED { n1(0), n2(1), n4(2), n8(3)
          } OPTIONAL
   ]]
}

DL-DataToUL-ACK-r16 ::= SEQUENCE (SIZE (1..8)) OF INTEGER (-1..15)

UL-AccessConfigListDCI-1-1-r16 ::= SEQUENCE (SIZE (1..16)) OF INTEGER (0..15)

DL-DataToUL-ACK-DCI-1-2-r16 ::= SEQUENCE (SIZE (1..8)) OF INTEGER (0..15)

PUCCH-SpatialRelationInfoExt-r16 ::= SEQUENCE {
   pucch-SpatialRelationInfoId-v1610 [0] PUCCH-SpatialRelationInfoId-v1610
       OPTIONAL, -- Need S
   pucch-PathlossReferenceRS-Id-v1610 [1] PUCCH-PathlossReferenceRS-Id-v1610
       OPTIONAL,
   ...
}

PUCCH-ResourceGroup-r16 ::= SEQUENCE {
   pucch-ResourceGroupId-r16 [0] PUCCH-ResourceGroupId-r16,
   resourcePerGroupList-r16 [1] SEQUENCE (SIZE (1..maxNrofPUCCH-ResourcesPerGroup-r16)) OF PUCCH-ResourceId
}

-- TAG-SPS-CONFIGINDEX-STOP
-- TAG-SPS-PUCCH-AN-START
SPS-PUCCH-AN-r16 ::= SEQUENCE {
   sps-PUCCH-AN-ResourceID-r16 [0] PUCCH-ResourceId,
   maxPayloadSize-r16 [1] INTEGER (4..256) OPTIONAL -- Need R
}

-- TAG-SPS-PUCCH-AN-STOP
-- TAG-SPS-PUCCH-AN-LIST-START
SPS-PUCCH-AN-List-r16 ::= SEQUENCE (SIZE (1..4)) OF SPS-PUCCH-AN-r16

SchedulingRequestResourceConfigExt-v1610 ::= SEQUENCE {
   phy-PriorityIndex-r16 [0] ENUMERATED { p0(0), p1(1) } OPTIONAL,
   ...
}

PUCCH-FormatConfigExt-r17 ::= SEQUENCE {
   maxCodeRateLP-r17 [0] PUCCH-MaxCodeRate OPTIONAL,
   ...
}

UL-AccessConfigListDCI-1-2-r17 ::= SEQUENCE (SIZE (1..16)) OF INTEGER (0..15)

PUCCH-PowerControlSetInfo-r17 ::= SEQUENCE {
   pucch-PowerControlSetInfoId-r17 [0] PUCCH-PowerControlSetInfoId-r17,
   p0-PUCCH-Id-r17 [1] P0-PUCCH-Id,
   pucch-ClosedLoopIndex-r17 [2] ENUMERATED { i0(0), i1(1) },
   pucch-PathlossReferenceRS-Id-r17 [3] PUCCH-PathlossReferenceRS-Id-r17
}

DL-DataToUL-ACK-r17 ::= SEQUENCE (SIZE (1..8)) OF INTEGER (-1..127)

DL-DataToUL-ACK-DCI-1-2-r17 ::= SEQUENCE (SIZE (1..8)) OF INTEGER (0..127)

UL-AccessConfigListDCI-1-1-r17 ::= SEQUENCE (SIZE (1..3)) OF INTEGER (0..2)

SchedulingRequestResourceConfigExt-v1700 ::= SEQUENCE {
   periodicityAndOffset-r17 [0] EXPLICIT CHOICE {
      sl1280 [0] INTEGER (0..1279),
      sl2560 [1] INTEGER (0..2559),
      sl5120 [2] INTEGER (0..5119)
   } OPTIONAL -- Need M
}

-- TAG-DL-PPW-PRECONFIG-STOP
-- TAG-DMRS-BUNDLINGPUCCH-CONFIG-START
DMRS-BundlingPUCCH-Config-r17 ::= SEQUENCE {
   pucch-DMRS-Bundling-r17 [0] ENUMERATED { enabled(0) } OPTIONAL, -- Need R
   pucch-TimeDomainWindowLength-r17 [1] INTEGER (2..8) OPTIONAL, -- Need S
   pucch-WindowRestart-r17 [2] ENUMERATED { enabled(0) } OPTIONAL, -- Need R
   pucch-FrequencyHoppingInterval-r17 [3] ENUMERATED { s2(0), s4(1), s5(2), 
      s10(3) } OPTIONAL,
   ...
}

DL-DataToUL-ACK-v1700 ::= SEQUENCE (SIZE (1..8)) OF INTEGER (16..31)

DL-DataToUL-ACK-MulticastDCI-Format4-1-r17 ::= SEQUENCE (SIZE (1..8)) OF INTEGER
    (0..15)

-- TAG-PTRS-UPLINKCONFIG-STOP
-- TAG-PUCCH-CONFIG-START
PUCCH-Config ::= SEQUENCE {
   resourceSetToAddModList [0] SEQUENCE (SIZE (1..maxNrofPUCCH-ResourceSets)) OF PUCCH-ResourceSet
       OPTIONAL, -- Need N
   resourceSetToReleaseList [1] SEQUENCE (SIZE (1..maxNrofPUCCH-ResourceSets)) OF PUCCH-ResourceSetId
       OPTIONAL, -- Need N
   resourceToAddModList [2] SEQUENCE (SIZE (1..maxNrofPUCCH-Resources)) OF PUCCH-Resource OPTIONAL, -- Need N
   resourceToReleaseList [3] SEQUENCE (SIZE (1..maxNrofPUCCH-Resources)) OF PUCCH-ResourceId OPTIONAL,
       -- Need N
   format1 [4] EXPLICIT CHOICE {
      release [0] NULL,
      setup [1] EXPLICIT PUCCH-FormatConfig
   } OPTIONAL, -- Need M
   format2 [5] EXPLICIT CHOICE {
      release [0] NULL,
      setup [1] EXPLICIT PUCCH-FormatConfig
   } OPTIONAL, -- Need M
   format3 [6] EXPLICIT CHOICE {
      release [0] NULL,
      setup [1] EXPLICIT PUCCH-FormatConfig
   } OPTIONAL, -- Need M
   format4 [7] EXPLICIT CHOICE {
      release [0] NULL,
      setup [1] EXPLICIT PUCCH-FormatConfig
   } OPTIONAL, -- Need M
   schedulingRequestResourceToAddModList [8] SEQUENCE (SIZE (1..maxNrofSR-Resources)) OF 
      SchedulingRequestResourceConfig OPTIONAL,
                                                                                                                             -- Need N
   schedulingRequestResourceToReleaseList [9] SEQUENCE (SIZE (1..maxNrofSR-Resources)) OF 
      SchedulingRequestResourceId OPTIONAL,
                                                                                                                             -- Need N
   multi-CSI-PUCCH-ResourceList [10] SEQUENCE (SIZE (1..2)) OF PUCCH-ResourceId
       OPTIONAL, -- Need M
   dl-DataToUL-ACK [11] SEQUENCE (SIZE (1..8)) OF INTEGER (0..15) OPTIONAL, -- Need M
   spatialRelationInfoToAddModList [12] SEQUENCE (SIZE (1..maxNrofSpatialRelationInfos)) OF 
      PUCCH-SpatialRelationInfo OPTIONAL,
                                                                                                                             -- Need N
   spatialRelationInfoToReleaseList [13] SEQUENCE (SIZE (1..maxNrofSpatialRelationInfos)) OF 
      PUCCH-SpatialRelationInfoId OPTIONAL,
                                                                                                                             -- Need N
   pucch-PowerControl [14] PUCCH-PowerControl OPTIONAL,
   ...,
   [[
      resourceToAddModListExt-v1610 [15] SEQUENCE (SIZE (1..maxNrofPUCCH-Resources)) OF 
         PUCCH-ResourceExt-v1610 OPTIONAL,
      dl-DataToUL-ACK-r16 [16] EXPLICIT CHOICE {
         release [0] NULL,
         setup [1] EXPLICIT DL-DataToUL-ACK-r16
      } OPTIONAL,
      ul-AccessConfigListDCI-1-1-r16 [17] EXPLICIT CHOICE {
         release [0] NULL,
         setup [1] EXPLICIT UL-AccessConfigListDCI-1-1-r16
      } OPTIONAL,
      subslotLengthForPUCCH-r16 [18] EXPLICIT CHOICE {
         normalCP-r16 [0] ENUMERATED { n2(0), n7(1) },
         extendedCP-r16 [1] ENUMERATED { n2(0), n6(1) }
      } OPTIONAL,
      dl-DataToUL-ACK-DCI-1-2-r16 [19] EXPLICIT CHOICE {
         release [0] NULL,
         setup [1] EXPLICIT DL-DataToUL-ACK-DCI-1-2-r16
      } OPTIONAL,
      numberOfBitsForPUCCH-ResourceIndicatorDCI-1-2-r16 [20] INTEGER (0..3)
          OPTIONAL,
      dmrs-UplinkTransformPrecodingPUCCH-r16 [21] ENUMERATED { enabled(0) }
          OPTIONAL,
      spatialRelationInfoToAddModListSizeExt-v1610 [22] SEQUENCE (SIZE (1..maxNrofSpatialRelationInfosDiff-r16)
         ) OF PUCCH-SpatialRelationInfo OPTIONAL,
      spatialRelationInfoToReleaseListSizeExt-v1610 [23] SEQUENCE (SIZE (1..maxNrofSpatialRelationInfosDiff-r16)
         ) OF PUCCH-SpatialRelationInfoId OPTIONAL,
      spatialRelationInfoToAddModListExt-v1610 [24] SEQUENCE (SIZE (1..maxNrofSpatialRelationInfos-r16)) OF 
         PUCCH-SpatialRelationInfoExt-r16 OPTIONAL,
      spatialRelationInfoToReleaseListExt-v1610 [25] SEQUENCE (SIZE (1..maxNrofSpatialRelationInfos-r16)) OF 
         PUCCH-SpatialRelationInfoId-r16 OPTIONAL,
      resourceGroupToAddModList-r16 [26] SEQUENCE (SIZE (1..maxNrofPUCCH-ResourceGroups-r16)) OF 
         PUCCH-ResourceGroup-r16 OPTIONAL,
      resourceGroupToReleaseList-r16 [27] SEQUENCE (SIZE (1..maxNrofPUCCH-ResourceGroups-r16)) OF 
         PUCCH-ResourceGroupId-r16 OPTIONAL,
      sps-PUCCH-AN-List-r16 [28] EXPLICIT CHOICE {
         release [0] NULL,
         setup [1] EXPLICIT SPS-PUCCH-AN-List-r16
      } OPTIONAL,
      schedulingRequestResourceToAddModListExt-v1610 [29] SEQUENCE (SIZE (1..maxNrofSR-Resources)
         ) OF SchedulingRequestResourceConfigExt-v1610 OPTIONAL
   ]],
   [[
      format0-r17 [30] EXPLICIT CHOICE {
         release [0] NULL,
         setup [1] EXPLICIT PUCCH-FormatConfig
      } OPTIONAL,
      format2Ext-r17 [31] EXPLICIT CHOICE {
         release [0] NULL,
         setup [1] EXPLICIT PUCCH-FormatConfigExt-r17
      } OPTIONAL,
      format3Ext-r17 [32] EXPLICIT CHOICE {
         release [0] NULL,
         setup [1] EXPLICIT PUCCH-FormatConfigExt-r17
      } OPTIONAL,
      format4Ext-r17 [33] EXPLICIT CHOICE {
         release [0] NULL,
         setup [1] EXPLICIT PUCCH-FormatConfigExt-r17
      } OPTIONAL,
      ul-AccessConfigListDCI-1-2-r17 [34] EXPLICIT CHOICE {
         release [0] NULL,
         setup [1] EXPLICIT UL-AccessConfigListDCI-1-2-r17
      } OPTIONAL,
      mappingPattern-r17 [35] ENUMERATED { cyclicMapping(0), 
         sequentialMapping(1) } OPTIONAL,
      powerControlSetInfoToAddModList-r17 [36] SEQUENCE (SIZE (1..maxNrofPowerControlSetInfos-r17)) OF 
         PUCCH-PowerControlSetInfo-r17 OPTIONAL,
      powerControlSetInfoToReleaseList-r17 [37] SEQUENCE (SIZE (1..maxNrofPowerControlSetInfos-r17)) OF 
         PUCCH-PowerControlSetInfoId-r17 OPTIONAL,
      secondTPCFieldDCI-1-1-r17 [38] ENUMERATED { enabled(0) } OPTIONAL,
      secondTPCFieldDCI-1-2-r17 [39] ENUMERATED { enabled(0) } OPTIONAL,
      dl-DataToUL-ACK-r17 [40] EXPLICIT CHOICE {
         release [0] NULL,
         setup [1] EXPLICIT DL-DataToUL-ACK-r17
      } OPTIONAL,
      dl-DataToUL-ACK-DCI-1-2-r17 [41] EXPLICIT CHOICE {
         release [0] NULL,
         setup [1] EXPLICIT DL-DataToUL-ACK-DCI-1-2-r17
      } OPTIONAL,
      ul-AccessConfigListDCI-1-1-r17 [42] EXPLICIT CHOICE {
         release [0] NULL,
         setup [1] EXPLICIT UL-AccessConfigListDCI-1-1-r17
      } OPTIONAL,
      schedulingRequestResourceToAddModListExt-v1700 [43] SEQUENCE (SIZE (1..maxNrofSR-Resources)
         ) OF SchedulingRequestResourceConfigExt-v1700 OPTIONAL,
      dmrs-BundlingPUCCH-Config-r17 [44] EXPLICIT CHOICE {
         release [0] NULL,
         setup [1] EXPLICIT DMRS-BundlingPUCCH-Config-r17
      } OPTIONAL,
      dl-DataToUL-ACK-v1700 [45] EXPLICIT CHOICE {
         release [0] NULL,
         setup [1] EXPLICIT DL-DataToUL-ACK-v1700
      } OPTIONAL,
      dl-DataToUL-ACK-MulticastDCI-Format4-1-r17 [46] EXPLICIT CHOICE {
         release [0] NULL,
         setup [1] EXPLICIT DL-DataToUL-ACK-MulticastDCI-Format4-1-r17
      } OPTIONAL,
      sps-PUCCH-AN-ListMulticast-r17 [47] EXPLICIT CHOICE {
         release [0] NULL,
         setup [1] EXPLICIT SPS-PUCCH-AN-List-r16
      } OPTIONAL
   ]]
}

PathlossReferenceRS-Config ::= CHOICE {
   ssb-Index [0] SSB-Index,
   csi-RS-Index [1] NZP-CSI-RS-ResourceId
}

PathlossReferenceRS-r16 ::= SEQUENCE {
   srs-PathlossReferenceRS-Id-r16 [0] SRS-PathlossReferenceRS-Id-r16,
   pathlossReferenceRS-r16 [1] EXPLICIT PathlossReferenceRS-Config
}

PathlossReferenceRSList-r16 ::= SEQUENCE (SIZE (1..maxNrofSRS-PathlossReferenceRS-r16)) OF PathlossReferenceRS-r16
   

SRS-ResourceSet ::= SEQUENCE {
   srs-ResourceSetId [0] SRS-ResourceSetId,
   srs-ResourceIdList [1] SEQUENCE (SIZE (1..maxNrofSRS-ResourcesPerSet)) OF SRS-ResourceId OPTIONAL, -- Cond Setup
   resourceType [2] EXPLICIT CHOICE {
      aperiodic [0] SEQUENCE {
         aperiodicSRS-ResourceTrigger [0] INTEGER (1..maxNrofSRS-TriggerStates-1),
         csi-RS [1] NZP-CSI-RS-ResourceId OPTIONAL, -- Cond NonCodebook
         slotOffset [2] INTEGER (1..32) OPTIONAL,
         ...,
         [[
            aperiodicSRS-ResourceTriggerList [3] SEQUENCE (SIZE (1..maxNrofSRS-TriggerStates-2)) OF 
               INTEGER (1..maxNrofSRS-TriggerStates-1) OPTIONAL
         ]]
      },
      semi-persistent [1] SEQUENCE {
         associatedCSI-RS [0] NZP-CSI-RS-ResourceId OPTIONAL,
         ...
      },
      periodic [2] SEQUENCE {
         associatedCSI-RS [0] NZP-CSI-RS-ResourceId OPTIONAL,
         ...
      }
   },
   usage [3] ENUMERATED { beamManagement(0), codebook(1), nonCodebook(2), 
      antennaSwitching(3) },
   alpha [4] Alpha OPTIONAL, -- Need S
   p0 [5] INTEGER (-202..24) OPTIONAL, -- Cond Setup
   pathlossReferenceRS [6] EXPLICIT PathlossReferenceRS-Config OPTIONAL, -- Need M
   srs-PowerControlAdjustmentStates [7] ENUMERATED { sameAsFci2(0), 
      separateClosedLoop(1) } OPTIONAL,
   ...,
   [[
      pathlossReferenceRSList-r16 [8] EXPLICIT CHOICE {
         release [0] NULL,
         setup [1] EXPLICIT PathlossReferenceRSList-r16
      } OPTIONAL
   ]],
   [[
      usagePDC-r17 [9] ENUMERATED { true(0) } OPTIONAL,
      availableSlotOffsetList-r17 [10] SEQUENCE (SIZE (1..4)) OF 
         AvailableSlotOffset-r17 OPTIONAL,
      followUnifiedTCI-StateSRS-r17 [11] ENUMERATED { enabled(0) } OPTIONAL
   ]]
}

SRS-PeriodicityAndOffset ::= CHOICE {
   sl1 [0] NULL,
   sl2 [1] INTEGER (0..1),
   sl4 [2] INTEGER (0..3),
   sl5 [3] INTEGER (0..4),
   sl8 [4] INTEGER (0..7),
   sl10 [5] INTEGER (0..9),
   sl16 [6] INTEGER (0..15),
   sl20 [7] INTEGER (0..19),
   sl32 [8] INTEGER (0..31),
   sl40 [9] INTEGER (0..39),
   sl64 [10] INTEGER (0..63),
   sl80 [11] INTEGER (0..79),
   sl160 [12] INTEGER (0..159),
   sl320 [13] INTEGER (0..319),
   sl640 [14] INTEGER (0..639),
   sl1280 [15] INTEGER (0..1279),
   sl2560 [16] INTEGER (0..2559)
}

SRS-SpatialRelationInfo ::= SEQUENCE {
   servingCellId [0] ServCellIndex OPTIONAL, -- Need S
   referenceSignal [1] EXPLICIT CHOICE {
      ssb-Index [0] SSB-Index,
      csi-RS-Index [1] NZP-CSI-RS-ResourceId,
      srs [2] SEQUENCE {
         resourceId [0] SRS-ResourceId,
         uplinkBWP [1] BWP-Id
      }
   }
}

SpatialRelationInfo-PDC-r17 ::= SEQUENCE {
   referenceSignal [0] EXPLICIT CHOICE {
      ssb-Index [0] SSB-Index,
      csi-RS-Index [1] NZP-CSI-RS-ResourceId,
      dl-PRS-PDC [2] NR-DL-PRS-ResourceID-r17,
      srs [3] SEQUENCE {
         resourceId [0] SRS-ResourceId,
         uplinkBWP [1] BWP-Id
      },
      ...
   },
   ...
}

SRS-Resource ::= SEQUENCE {
   srs-ResourceId [0] SRS-ResourceId,
   nrofSRS-Ports [1] ENUMERATED { port1(0), ports2(1), ports4(2) },
   ptrs-PortIndex [2] ENUMERATED { n0(0), n1(1) } OPTIONAL, -- Need R
   transmissionComb [3] EXPLICIT CHOICE {
      n2 [0] SEQUENCE {
         combOffset-n2 [0] INTEGER (0..1),
         cyclicShift-n2 [1] INTEGER (0..7)
      },
      n4 [1] SEQUENCE {
         combOffset-n4 [0] INTEGER (0..3),
         cyclicShift-n4 [1] INTEGER (0..11)
      }
   },
   resourceMapping [4] SEQUENCE {
      startPosition [0] INTEGER (0..5),
      nrofSymbols [1] ENUMERATED { n1(0), n2(1), n4(2) },
      repetitionFactor [2] ENUMERATED { n1(0), n2(1), n4(2) }
   },
   freqDomainPosition [5] INTEGER (0..67),
   freqDomainShift [6] INTEGER (0..268),
   freqHopping [7] SEQUENCE {
      c-SRS [0] INTEGER (0..63),
      b-SRS [1] INTEGER (0..3),
      b-hop [2] INTEGER (0..3)
   },
   groupOrSequenceHopping [8] ENUMERATED { neither(0), groupHopping(1), 
      sequenceHopping(2) },
   resourceType [9] EXPLICIT CHOICE {
      aperiodic [0] SEQUENCE {

         ...
      },
      semi-persistent [1] SEQUENCE {
         periodicityAndOffset-sp [0] EXPLICIT SRS-PeriodicityAndOffset,
         ...
      },
      periodic [2] SEQUENCE {
         periodicityAndOffset-p [0] EXPLICIT SRS-PeriodicityAndOffset,
         ...
      }
   },
   sequenceId [10] INTEGER (0..1023),
   spatialRelationInfo [11] SRS-SpatialRelationInfo OPTIONAL,
   ...,
   [[
      resourceMapping-r16 [12] SEQUENCE {
         startPosition-r16 [0] INTEGER (0..13),
         nrofSymbols-r16 [1] ENUMERATED { n1(0), n2(1), n4(2) },
         repetitionFactor-r16 [2] ENUMERATED { n1(0), n2(1), n4(2) }
      } OPTIONAL
   ]],
   [[
      spatialRelationInfo-PDC-r17 [13] EXPLICIT CHOICE {
         release [0] NULL,
         setup [1] EXPLICIT SpatialRelationInfo-PDC-r17
      } OPTIONAL,
      resourceMapping-r17 [14] SEQUENCE {
         startPosition-r17 [0] INTEGER (0..13),
         nrofSymbols-r17 [1] ENUMERATED { n1(0), n2(1), n4(2), n8(3), n10(4), 
            n12(5), n14(6) },
         repetitionFactor-r17 [2] ENUMERATED { n1(0), n2(1), n4(2), n5(3), 
            n6(4), n7(5), n8(6), n10(7), n12(8), n14(9) }
      } OPTIONAL,
      partialFreqSounding-r17 [15] SEQUENCE {
         startRBIndexFScaling-r17 [0] EXPLICIT CHOICE {
            startRBIndexAndFreqScalingFactor2-r17 [0] INTEGER (0..1),
            startRBIndexAndFreqScalingFactor4-r17 [1] INTEGER (0..3)
         },
         enableStartRBHopping-r17 [1] ENUMERATED { enable(0) } OPTIONAL -- Need R
      } OPTIONAL,
      transmissionComb-n8-r17 [16] SEQUENCE {
         combOffset-n8-r17 [0] INTEGER (0..7),
         cyclicShift-n8-r17 [1] INTEGER (0..5)
      } OPTIONAL,
      srs-TCI-State-r17 [17] EXPLICIT CHOICE {
         srs-UL-TCI-State [0] TCI-UL-StateId-r17,
         srs-DLorJointTCI-State [1] TCI-StateId
      } OPTIONAL
   ]],
   [[
      repetitionFactor-v1730 [18] ENUMERATED { n3(0) } OPTIONAL,
      srs-DLorJointTCI-State-v1730 [19] SEQUENCE {
         cellAndBWP-r17 [0] ServingCellAndBWP-Id-r17
      } OPTIONAL
   ]]
}

-- TAG-SRS-CARRIERSWITCHING-STOP
-- TAG-SRS-CONFIG-START
SRS-Config ::= SEQUENCE {
   srs-ResourceSetToReleaseList [0] SEQUENCE (SIZE (1..maxNrofSRS-ResourceSets)) OF SRS-ResourceSetId
       OPTIONAL, -- Need N
   srs-ResourceSetToAddModList [1] SEQUENCE (SIZE (1..maxNrofSRS-ResourceSets)) OF SRS-ResourceSet
       OPTIONAL, -- Need N
   srs-ResourceToReleaseList [2] SEQUENCE (SIZE (1..maxNrofSRS-Resources)) OF SRS-ResourceId
       OPTIONAL, -- Need N
   srs-ResourceToAddModList [3] SEQUENCE (SIZE (1..maxNrofSRS-Resources)) OF SRS-Resource OPTIONAL, -- Need N
   tpc-Accumulation [4] ENUMERATED { disabled(0) } OPTIONAL,
   ...,
   [[
      srs-RequestDCI-1-2-r16 [5] INTEGER (1..2) OPTIONAL,
      srs-RequestDCI-0-2-r16 [6] INTEGER (1..2) OPTIONAL,
      srs-ResourceSetToAddModListDCI-0-2-r16 [7] SEQUENCE (SIZE (1..maxNrofSRS-ResourceSets)) OF 
         SRS-ResourceSet OPTIONAL,
      srs-ResourceSetToReleaseListDCI-0-2-r16 [8] SEQUENCE (SIZE (1..maxNrofSRS-ResourceSets)) OF 
         SRS-ResourceSetId OPTIONAL,
      srs-PosResourceSetToReleaseList-r16 [9] SEQUENCE (SIZE (1..maxNrofSRS-PosResourceSets-r16)) OF 
         SRS-PosResourceSetId-r16 OPTIONAL,
      srs-PosResourceSetToAddModList-r16 [10] SEQUENCE (SIZE (1..maxNrofSRS-PosResourceSets-r16)) OF 
         SRS-PosResourceSet-r16 OPTIONAL,
      srs-PosResourceToReleaseList-r16 [11] SEQUENCE (SIZE (1..maxNrofSRS-PosResources-r16)) OF 
         SRS-PosResourceId-r16 OPTIONAL,
      srs-PosResourceToAddModList-r16 [12] SEQUENCE (SIZE (1..maxNrofSRS-PosResources-r16)) OF 
         SRS-PosResource-r16 OPTIONAL
   ]]
}

BFR-SSB-Resource ::= SEQUENCE {
   ssb [0] SSB-Index,
   ra-PreambleIndex [1] INTEGER (0..63),
   ...
}

BFR-CSIRS-Resource ::= SEQUENCE {
   csi-RS [0] NZP-CSI-RS-ResourceId,
   ra-OccasionList [1] SEQUENCE (SIZE (1..maxRA-OccasionsPerCSIRS)) OF INTEGER (0..maxRA-Occasions-1) OPTIONAL, -- Need R
   ra-PreambleIndex [2] INTEGER (0..63) OPTIONAL,
   ...
}

PRACH-ResourceDedicatedBFR ::= CHOICE {
   ssb [0] BFR-SSB-Resource,
   csi-RS [1] BFR-CSIRS-Resource
}

CandidateBeamRSListExt-r16 ::= SEQUENCE (SIZE (1..maxNrofCandidateBeamsExt-r16)) OF 
   PRACH-ResourceDedicatedBFR

-- TAG-BAPROUTINGID-STOP
-- TAG-BEAMFAILURERECOVERYCONFIG-START
BeamFailureRecoveryConfig ::= SEQUENCE {
   rootSequenceIndex-BFR [0] INTEGER (0..137) OPTIONAL, -- Need M
   rach-ConfigBFR [1] RACH-ConfigGeneric OPTIONAL, -- Need M
   rsrp-ThresholdSSB [2] RSRP-Range OPTIONAL, -- Need M
   candidateBeamRSList [3] SEQUENCE (SIZE (1..maxNrofCandidateBeams)) OF PRACH-ResourceDedicatedBFR
       OPTIONAL, -- Need M
   ssb-perRACH-Occasion [4] ENUMERATED { oneEighth(0), oneFourth(1), oneHalf(2)
      , one(3), two(4), four(5), eight(6), sixteen(7) } OPTIONAL, -- Need M
   ra-ssb-OccasionMaskIndex [5] INTEGER (0..15) OPTIONAL, -- Need M
   recoverySearchSpaceId [6] SearchSpaceId OPTIONAL, -- Need R
   ra-Prioritization [7] RA-Prioritization OPTIONAL, -- Need R
   beamFailureRecoveryTimer [8] ENUMERATED { ms10(0), ms20(1), ms40(2), ms60(3)
      , ms80(4), ms100(5), ms150(6), ms200(7) } OPTIONAL,
   ...,
   [[
      msg1-SubcarrierSpacing [9] SubcarrierSpacing OPTIONAL
   ]],
   [[
      ra-PrioritizationTwoStep-r16 [10] RA-Prioritization OPTIONAL,
      candidateBeamRSListExt-v1610 [11] EXPLICIT CHOICE {
         release [0] NULL,
         setup [1] EXPLICIT CandidateBeamRSListExt-r16
      } OPTIONAL
   ]],
   [[
      spCell-BFR-CBRA-r16 [12] ENUMERATED { true(0) } OPTIONAL
   ]]
}

-- TAG-PUCCH-CONFIGCOMMON-STOP
-- TAG-PUCCH-CONFIGURATIONLIST-START
PUCCH-ConfigurationList-r16 ::= SEQUENCE (SIZE (1..2)) OF PUCCH-Config

-- TAG-I-RNTI-VALUE-STOP
-- TAG-LBT-FAILURERECOVERYCONFIG-START
LBT-FailureRecoveryConfig-r16 ::= SEQUENCE {
   lbt-FailureInstanceMaxCount-r16 [0] ENUMERATED { n4(0), n8(1), n16(2), 
      n32(3), n64(4), n128(5) },
   lbt-FailureDetectionTimer-r16 [1] ENUMERATED { ms10(0), ms20(1), ms40(2), 
      ms80(3), ms160(4), ms320(5) },
   ...
}

ConfiguredGrantConfigType2DeactivationState-r16 ::= SEQUENCE (SIZE (1..maxNrofConfiguredGrantConfig-r16)) OF 
   ConfiguredGrantConfigIndex-r16

ConfiguredGrantConfigType2DeactivationStateList-r16 ::= SEQUENCE (SIZE (1..maxNrofCG-Type2DeactivationState)
   ) OF ConfiguredGrantConfigType2DeactivationState-r16

-- TAG-TCI-STATEID-STOP
-- TAG-TCI-UL-STATE-START
TCI-UL-State-r17 ::= SEQUENCE {
   tci-UL-StateId-r17 [0] TCI-UL-StateId-r17,
   servingCellId-r17 [1] ServCellIndex OPTIONAL, -- Need R
   bwp-Id-r17 [2] BWP-Id OPTIONAL, -- Cond CSI-RSorSRS-Indicated
   referenceSignal-r17 [3] EXPLICIT CHOICE {
      ssb-Index-r17 [0] SSB-Index,
      csi-RS-Index-r17 [1] NZP-CSI-RS-ResourceId,
      srs-r17 [2] SRS-ResourceId
   },
   additionalPCI-r17 [4] AdditionalPCIIndex-r17 OPTIONAL, -- Need R
   ul-powerControl-r17 [5] Uplink-powerControlId-r17 OPTIONAL, -- Need R
   pathlossReferenceRS-Id-r17 [6] PathlossReferenceRS-Id-r17 OPTIONAL,
   ...
}

-- TAG-P-MAX-STOP
-- TAG-PATHLOSSREFERENCERS-START
PathlossReferenceRS-r17 ::= SEQUENCE {
   pathlossReferenceRS-Id-r17 [0] PathlossReferenceRS-Id-r17,
   referenceSignal-r17 [1] EXPLICIT CHOICE {
      ssb-Index [0] SSB-Index,
      csi-RS-Index [1] NZP-CSI-RS-ResourceId
   },
   additionalPCI-r17 [2] AdditionalPCIIndex-r17 OPTIONAL -- Cond RS-SSB
}

-- TAG-BWP-UPLINKCOMMON-STOP
-- TAG-BWP-UPLINKDEDICATED-START
BWP-UplinkDedicated ::= SEQUENCE {
   pucch-Config [0] EXPLICIT CHOICE {
      release [0] NULL,
      setup [1] EXPLICIT PUCCH-Config
   } OPTIONAL, -- Need M
   pusch-Config [1] EXPLICIT CHOICE {
      release [0] NULL,
      setup [1] EXPLICIT PUSCH-Config
   } OPTIONAL, -- Need M
   configuredGrantConfig [2] EXPLICIT CHOICE {
      release [0] NULL,
      setup [1] EXPLICIT ConfiguredGrantConfig
   } OPTIONAL, -- Need M
   srs-Config [3] EXPLICIT CHOICE {
      release [0] NULL,
      setup [1] EXPLICIT SRS-Config
   } OPTIONAL, -- Need M
   beamFailureRecoveryConfig [4] EXPLICIT CHOICE {
      release [0] NULL,
      setup [1] EXPLICIT BeamFailureRecoveryConfig
   } OPTIONAL,
   ...,
   [[
      sl-PUCCH-Config-r16 [5] EXPLICIT CHOICE {
         release [0] NULL,
         setup [1] EXPLICIT PUCCH-Config
      } OPTIONAL,
      cp-ExtensionC2-r16 [6] INTEGER (1..28) OPTIONAL,
      cp-ExtensionC3-r16 [7] INTEGER (1..28) OPTIONAL,
      useInterlacePUCCH-PUSCH-r16 [8] ENUMERATED { enabled(0) } OPTIONAL,
      pucch-ConfigurationList-r16 [9] EXPLICIT CHOICE {
         release [0] NULL,
         setup [1] EXPLICIT PUCCH-ConfigurationList-r16
      } OPTIONAL,
      lbt-FailureRecoveryConfig-r16 [10] EXPLICIT CHOICE {
         release [0] NULL,
         setup [1] EXPLICIT LBT-FailureRecoveryConfig-r16
      } OPTIONAL,
      configuredGrantConfigToAddModList-r16 [11] 
         ConfiguredGrantConfigToAddModList-r16 OPTIONAL,
      configuredGrantConfigToReleaseList-r16 [12] 
         ConfiguredGrantConfigToReleaseList-r16 OPTIONAL,
      configuredGrantConfigType2DeactivationStateList-r16 [13] 
         ConfiguredGrantConfigType2DeactivationStateList-r16 OPTIONAL
   ]],
   [[
      ul-TCI-StateList-r17 [14] EXPLICIT CHOICE {
         explicitlist [0] SEQUENCE {
            ul-TCI-ToAddModList-r17 [0] SEQUENCE (SIZE (1..maxUL-TCI-r17)) OF 
               TCI-UL-State-r17 OPTIONAL, -- Need N
            ul-TCI-ToReleaseList-r17 [1] SEQUENCE (SIZE (1..maxUL-TCI-r17)) OF 
               TCI-UL-StateId-r17 OPTIONAL -- Need N
         },
         unifiedTCI-StateRef-r17 [1] ServingCellAndBWP-Id-r17
      } OPTIONAL,
      ul-powerControl-r17 [15] Uplink-powerControlId-r17 OPTIONAL,
      pucch-ConfigurationListMulticast1-r17 [16] EXPLICIT CHOICE {
         release [0] NULL,
         setup [1] EXPLICIT PUCCH-ConfigurationList-r16
      } OPTIONAL,
      pucch-ConfigurationListMulticast2-r17 [17] EXPLICIT CHOICE {
         release [0] NULL,
         setup [1] EXPLICIT PUCCH-ConfigurationList-r16
      } OPTIONAL
   ]],
   [[
      pucch-ConfigMulticast1-r17 [18] EXPLICIT CHOICE {
         release [0] NULL,
         setup [1] EXPLICIT PUCCH-Config
      } OPTIONAL,
      pucch-ConfigMulticast2-r17 [19] EXPLICIT CHOICE {
         release [0] NULL,
         setup [1] EXPLICIT PUCCH-Config
      } OPTIONAL
   ]],
   [[
      pathlossReferenceRSToAddModList-r17 [20] SEQUENCE (SIZE (1..maxNrofPathlossReferenceRSs-r17)) OF 
         PathlossReferenceRS-r17 OPTIONAL,
      pathlossReferenceRSToReleaseList-r17 [21] SEQUENCE (SIZE (1..maxNrofPathlossReferenceRSs-r17)) OF 
         PathlossReferenceRS-Id-r17 OPTIONAL
   ]]
}

-- TAG-BWP-ID-STOP
-- TAG-BWP-UPLINK-START
BWP-Uplink ::= SEQUENCE {
   bwp-Id [0] BWP-Id,
   bwp-Common [1] BWP-UplinkCommon OPTIONAL, -- Cond SetupOtherBWP
   bwp-Dedicated [2] BWP-UplinkDedicated OPTIONAL,
   ...
}

PUSCH-CodeBlockGroupTransmission ::= SEQUENCE {
   maxCodeBlockGroupsPerTransportBlock [0] ENUMERATED { n2(0), n4(1), n6(2), 
      n8(3) },
   ...
}

-- TAG-PUSCH-POWERCONTROL-STOP
-- TAG-PUSCH-SERVINGCELLCONFIG-START
PUSCH-ServingCellConfig ::= SEQUENCE {
   codeBlockGroupTransmission [0] EXPLICIT CHOICE {
      release [0] NULL,
      setup [1] EXPLICIT PUSCH-CodeBlockGroupTransmission
   } OPTIONAL, -- Need M
   rateMatching [1] ENUMERATED { limitedBufferRM(0) } OPTIONAL, -- Need S
   xOverhead [2] ENUMERATED { xoh6(0), xoh12(1), xoh18(2) } OPTIONAL,
   ...,
   [[
      maxMIMO-Layers [3] INTEGER (1..4) OPTIONAL,
      processingType2Enabled [4] BOOLEAN OPTIONAL
   ]],
   [[
      maxMIMO-LayersDCI-0-2-r16 [5] EXPLICIT CHOICE {
         release [0] NULL,
         setup [1] EXPLICIT MaxMIMO-LayersDCI-0-2-r16
      } OPTIONAL
   ]],
   [[
      nrofHARQ-ProcessesForPUSCH-r17 [6] ENUMERATED { n32(0) } OPTIONAL,
      uplinkHARQ-mode-r17 [7] EXPLICIT CHOICE {
         release [0] NULL,
         setup [1] EXPLICIT UplinkHARQ-mode-r17
      } OPTIONAL
   ]]
}

SRS-CC-SetIndex ::= SEQUENCE {
   cc-SetIndex [0] INTEGER (0..3) OPTIONAL, -- Need M
   cc-IndexInOneCC-Set [1] INTEGER (0..7) OPTIONAL -- Need M
}

SRS-TPC-PDCCH-Config ::= SEQUENCE {
   srs-CC-SetIndexlist [0] SEQUENCE (SIZE (1..4)) OF SRS-CC-SetIndex OPTIONAL -- Need M
}

-- TAG-SRB-IDENTITY-STOP
-- TAG-SRS-CARRIERSWITCHING-START
SRS-CarrierSwitching ::= SEQUENCE {
   srs-SwitchFromServCellIndex [0] INTEGER (0..31) OPTIONAL, -- Need M
   srs-SwitchFromCarrier [1] ENUMERATED { sUL(0), nUL(1) },
   srs-TPC-PDCCH-Group [2] EXPLICIT CHOICE {
      typeA [0] SEQUENCE (SIZE (1..32)) OF SRS-TPC-PDCCH-Config,
      typeB [1] SRS-TPC-PDCCH-Config
   } OPTIONAL, -- Need M
   monitoringCells [3] SEQUENCE (SIZE (1..maxNrofServingCells)) OF ServCellIndex OPTIONAL,
   ...
}

UplinkTxSwitching-r16 ::= SEQUENCE {
   uplinkTxSwitchingPeriodLocation-r16 [0] BOOLEAN,
   uplinkTxSwitchingCarrier-r16 [1] ENUMERATED { carrier1(0), carrier2(1) }
}

UplinkConfig ::= SEQUENCE {
   initialUplinkBWP [0] BWP-UplinkDedicated OPTIONAL, -- Need M
   uplinkBWP-ToReleaseList [1] SEQUENCE (SIZE (1..maxNrofBWPs)) OF BWP-Id OPTIONAL, -- Need N
   uplinkBWP-ToAddModList [2] SEQUENCE (SIZE (1..maxNrofBWPs)) OF BWP-Uplink OPTIONAL, -- Need N
   firstActiveUplinkBWP-Id [3] BWP-Id OPTIONAL, -- Cond SyncAndCellAdd
   pusch-ServingCellConfig [4] EXPLICIT CHOICE {
      release [0] NULL,
      setup [1] EXPLICIT PUSCH-ServingCellConfig
   } OPTIONAL, -- Need M
   carrierSwitching [5] EXPLICIT CHOICE {
      release [0] NULL,
      setup [1] EXPLICIT SRS-CarrierSwitching
   } OPTIONAL,
   ...,
   [[
      powerBoostPi2BPSK [6] BOOLEAN OPTIONAL,
      uplinkChannelBW-PerSCS-List [7] SEQUENCE (SIZE (1..maxSCSs)) OF 
         SCS-SpecificCarrier OPTIONAL
   ]],
   [[
      enablePL-RS-UpdateForPUSCH-SRS-r16 [8] ENUMERATED { enabled(0) } OPTIONAL
         ,
      enableDefaultBeamPL-ForPUSCH0-0-r16 [9] ENUMERATED { enabled(0) }
          OPTIONAL,
      enableDefaultBeamPL-ForPUCCH-r16 [10] ENUMERATED { enabled(0) } OPTIONAL
         ,
      enableDefaultBeamPL-ForSRS-r16 [11] ENUMERATED { enabled(0) } OPTIONAL,
      uplinkTxSwitching-r16 [12] EXPLICIT CHOICE {
         release [0] NULL,
         setup [1] EXPLICIT UplinkTxSwitching-r16
      } OPTIONAL,
      mpr-PowerBoost-FR2-r16 [13] ENUMERATED { true(0) } OPTIONAL
   ]]
}

SlotFormatCombination ::= SEQUENCE {
   slotFormatCombinationId [0] SlotFormatCombinationId,
   slotFormats [1] SEQUENCE (SIZE (1..maxNrofSlotFormatsPerCombination)) OF INTEGER (0..255)
}

-- TAG-SKCOUNTER-STOP
-- TAG-SLOTFORMATCOMBINATIONSPERCELL-START
SlotFormatCombinationsPerCell ::= SEQUENCE {
   servingCellId [0] ServCellIndex,
   subcarrierSpacing [1] SubcarrierSpacing,
   subcarrierSpacing2 [2] SubcarrierSpacing OPTIONAL, -- Need R
   slotFormatCombinations [3] SEQUENCE (SIZE (1..maxNrofSlotFormatCombinationsPerSet)) OF SlotFormatCombination
       OPTIONAL,
                                                                                                                             -- Need M
   positionInDCI [4] INTEGER (0..maxSFI-DCI-PayloadSize-1) OPTIONAL,
   ...,
   [[
      enableConfiguredUL-r16 [5] ENUMERATED { enabled(0) } OPTIONAL
   ]]
}

AvailableRB-SetsPerCell-r16 ::= SEQUENCE {
   servingCellId-r16 [0] ServCellIndex,
   positionInDCI-r16 [1] INTEGER (0..maxSFI-DCI-PayloadSize-1)
}

SearchSpaceSwitchTrigger-r16 ::= SEQUENCE {
   servingCellId-r16 [0] ServCellIndex,
   positionInDCI-r16 [1] INTEGER (0..maxSFI-DCI-PayloadSize-1)
}

CO-DurationsPerCell-r16 ::= SEQUENCE {
   servingCellId-r16 [0] ServCellIndex,
   positionInDCI-r16 [1] INTEGER (0..maxSFI-DCI-PayloadSize-1),
   subcarrierSpacing-r16 [2] SubcarrierSpacing,
   co-DurationList-r16 [3] SEQUENCE (SIZE (1..64)) OF CO-Duration-r16
}

CO-DurationsPerCell-r17 ::= SEQUENCE {
   servingCellId-r17 [0] ServCellIndex,
   positionInDCI-r17 [1] INTEGER (0..maxSFI-DCI-PayloadSize-1),
   subcarrierSpacing-r17 [2] SubcarrierSpacing,
   co-DurationList-r17 [3] SEQUENCE (SIZE (1..64)) OF CO-Duration-r17
}

-- TAG-SLOTFORMATCOMBINATIONSPERCELL-STOP
-- TAG-SLOTFORMATINDICATOR-START
SlotFormatIndicator ::= SEQUENCE {
   sfi-RNTI [0] RNTI-Value,
   dci-PayloadSize [1] INTEGER (1..maxSFI-DCI-PayloadSize),
   slotFormatCombToAddModList [2] SEQUENCE (SIZE (1..maxNrofAggregatedCellsPerCellGroup)) OF 
      SlotFormatCombinationsPerCell OPTIONAL,
                                                                                                                                         -- Need N
   slotFormatCombToReleaseList [3] SEQUENCE (SIZE (1..maxNrofAggregatedCellsPerCellGroup)) OF ServCellIndex
       OPTIONAL,
   ...,
   [[
      availableRB-SetsToAddModList-r16 [4] SEQUENCE (SIZE (1..maxNrofAggregatedCellsPerCellGroup)) OF 
         AvailableRB-SetsPerCell-r16 OPTIONAL,
      availableRB-SetsToReleaseList-r16 [5] SEQUENCE (SIZE (1..maxNrofAggregatedCellsPerCellGroup)) OF 
         ServCellIndex OPTIONAL,
      switchTriggerToAddModList-r16 [6] SEQUENCE (SIZE (1..4)) OF 
         SearchSpaceSwitchTrigger-r16 OPTIONAL,
      switchTriggerToReleaseList-r16 [7] SEQUENCE (SIZE (1..4)) OF ServCellIndex
          OPTIONAL,
      co-DurationsPerCellToAddModList-r16 [8] SEQUENCE (SIZE (1..maxNrofAggregatedCellsPerCellGroup)) OF 
         CO-DurationsPerCell-r16 OPTIONAL,
      co-DurationsPerCellToReleaseList-r16 [9] SEQUENCE (SIZE (1..maxNrofAggregatedCellsPerCellGroup)) OF 
         ServCellIndex OPTIONAL
   ]],
   [[
      switchTriggerToAddModListSizeExt-r16 [10] SEQUENCE (SIZE (1..maxNrofAggregatedCellsPerCellGroupMinus4-r16)) OF 
         SearchSpaceSwitchTrigger-r16 OPTIONAL,
      switchTriggerToReleaseListSizeExt-r16 [11] SEQUENCE (SIZE (1..maxNrofAggregatedCellsPerCellGroupMinus4-r16)) OF 
         ServCellIndex OPTIONAL
   ]],
   [[
      co-DurationsPerCellToAddModList-r17 [12] SEQUENCE (SIZE (1..maxNrofAggregatedCellsPerCellGroup)) OF 
         CO-DurationsPerCell-r17 OPTIONAL
   ]]
}

AvailabilityCombination-r16 ::= SEQUENCE {
   availabilityCombinationId-r16 [0] AvailabilityCombinationId-r16,
   resourceAvailability-r16 [1] SEQUENCE (SIZE (1..maxNrofResourceAvailabilityPerCombination-r16)) OF INTEGER (0..7)
}

RB-SetGroup-r17 ::= SEQUENCE {
   resourceAvailability-r17 [0] SEQUENCE (SIZE (1..maxNrofResourceAvailabilityPerCombination-r16)) OF INTEGER (0..7) OPTIONAL, -- Need R
   rb-Sets-r17 [1] SEQUENCE (SIZE (1..maxNrofRB-Sets-r17)) OF INTEGER (0..7) OPTIONAL -- Need R
}

AvailabilityCombinationRB-Groups-r17 ::= SEQUENCE {
   availabilityCombinationId-r17 [0] AvailabilityCombinationId-r16,
   rb-SetGroups-r17 [1] SEQUENCE (SIZE (1..maxNrofRB-SetGroups-r17)) OF RB-SetGroup-r17 OPTIONAL, -- Need R
   resourceAvailability-r17 [2] SEQUENCE (SIZE (1..maxNrofResourceAvailabilityPerCombination-r16)) OF INTEGER (0..7) OPTIONAL -- Need R
}

-- TAG-ARFCN-ValueUTRA-FDD-STOP
-- TAG-AVAILABILITYCOMBINATIONSPERCELL-START
AvailabilityCombinationsPerCell-r16 ::= SEQUENCE {
   availabilityCombinationsPerCellIndex-r16 [0] 
      AvailabilityCombinationsPerCellIndex-r16,
   iab-DU-CellIdentity-r16 [1] CellIdentity,
   positionInDCI-AI-r16 [2] INTEGER (0..maxAI-DCI-PayloadSize-1-r16) OPTIONAL, -- Need M
   availabilityCombinations-r16 [3] SEQUENCE (SIZE (1..maxNrofAvailabilityCombinationsPerSet-r16)) OF 
      AvailabilityCombination-r16,
   ...,
   [[
      availabilityCombinationsRB-Groups-r17 [4] SEQUENCE (SIZE (1..maxNrofAvailabilityCombinationsPerSet-r16)) OF 
         AvailabilityCombinationRB-Groups-r17 OPTIONAL
   ]],
   [[
      positionInDCI-AI-RBGroups-v1720 [5] INTEGER (0..maxAI-DCI-PayloadSize-1-r16) OPTIONAL
   ]]
}

-- TAG-AVAILABILITYCOMBINATIONSPERCELL-STOP
-- TAG-AVAILABILITYINDICATOR-START
AvailabilityIndicator-r16 ::= SEQUENCE {
   ai-RNTI-r16 [0] AI-RNTI-r16,
   dci-PayloadSizeAI-r16 [1] INTEGER (1..maxAI-DCI-PayloadSize-r16),
   availableCombToAddModList-r16 [2] SEQUENCE (SIZE (1..maxNrofDUCells-r16)) OF 
      AvailabilityCombinationsPerCell-r16 OPTIONAL, -- Need N
   availableCombToReleaseList-r16 [3] SEQUENCE (SIZE (1..maxNrofDUCells-r16)) OF 
      AvailabilityCombinationsPerCellIndex-r16 OPTIONAL,
   ...
}

-- TAG-PDCCH-CONFIGSIB1-STOP
-- TAG-PDCCH-SERVINGCELLCONFIG-START
PDCCH-ServingCellConfig ::= SEQUENCE {
   slotFormatIndicator [0] EXPLICIT CHOICE {
      release [0] NULL,
      setup [1] EXPLICIT SlotFormatIndicator
   } OPTIONAL,
   ...,
   [[
      availabilityIndicator-r16 [1] EXPLICIT CHOICE {
         release [0] NULL,
         setup [1] EXPLICIT AvailabilityIndicator-r16
      } OPTIONAL,
      searchSpaceSwitchTimer-r16 [2] INTEGER (1..80) OPTIONAL
   ]],
   [[
      searchSpaceSwitchTimer-v1710 [3] INTEGER (81..1280) OPTIONAL
   ]]
}

PDSCH-CodeBlockGroupTransmission ::= SEQUENCE {
   maxCodeBlockGroupsPerTransportBlock [0] ENUMERATED { n2(0), n4(1), n6(2), 
      n8(3) },
   codeBlockGroupFlushIndicator [1] BOOLEAN,
   ...
}

PDSCH-CodeBlockGroupTransmissionList-r16 ::= SEQUENCE (SIZE (1..2)) OF 
   PDSCH-CodeBlockGroupTransmission

-- TAG-PDSCH-CONFIGCOMMON-STOP
-- TAG-PDSCH-SERVINGCELLCONFIG-START
PDSCH-ServingCellConfig ::= SEQUENCE {
   codeBlockGroupTransmission [0] EXPLICIT CHOICE {
      release [0] NULL,
      setup [1] EXPLICIT PDSCH-CodeBlockGroupTransmission
   } OPTIONAL, -- Need M
   xOverhead [1] ENUMERATED { xOh6(0), xOh12(1), xOh18(2) } OPTIONAL, -- Need S
   nrofHARQ-ProcessesForPDSCH [2] ENUMERATED { n2(0), n4(1), n6(2), n10(3), 
      n12(4), n16(5) } OPTIONAL, -- Need S
   pucch-Cell [3] ServCellIndex OPTIONAL,
   ...,
   [[
      maxMIMO-Layers [4] INTEGER (1..8) OPTIONAL,
      processingType2Enabled [5] BOOLEAN OPTIONAL
   ]],
   [[
      pdsch-CodeBlockGroupTransmissionList-r16 [6] EXPLICIT CHOICE {
         release [0] NULL,
         setup [1] EXPLICIT PDSCH-CodeBlockGroupTransmissionList-r16
      } OPTIONAL
   ]],
   [[
      downlinkHARQ-FeedbackDisabled-r17 [7] EXPLICIT CHOICE {
         release [0] NULL,
         setup [1] EXPLICIT DownlinkHARQ-FeedbackDisabled-r17
      } OPTIONAL,
      nrofHARQ-ProcessesForPDSCH-v1700 [8] ENUMERATED { n32(0) } OPTIONAL
   ]]
}

-- TAG-NTN-CONFIG-STOP
-- TAG-NZP-CSI-RS-RESOURCE-START
NZP-CSI-RS-Resource ::= SEQUENCE {
   nzp-CSI-RS-ResourceId [0] NZP-CSI-RS-ResourceId,
   resourceMapping [1] CSI-RS-ResourceMapping,
   powerControlOffset [2] INTEGER (-8..15),
   powerControlOffsetSS [3] ENUMERATED { db-3(0), db0(1), db3(2), db6(3) }
       OPTIONAL, -- Need R
   scramblingID [4] ScramblingId,
   periodicityAndOffset [5] EXPLICIT CSI-ResourcePeriodicityAndOffset OPTIONAL,
       -- Cond PeriodicOrSemiPersistent
   qcl-InfoPeriodicCSI-RS [6] TCI-StateId OPTIONAL,
   ...
}

NZP-CSI-RS-Pairing-r17 ::= SEQUENCE {
   nzp-CSI-RS-ResourceId1-r17 [0] INTEGER (1..7),
   nzp-CSI-RS-ResourceId2-r17 [1] INTEGER (1..7)
}

CMRGroupingAndPairing-r17 ::= SEQUENCE {
   nrofResourcesGroup1-r17 [0] INTEGER (1..7),
   pair1OfNZP-CSI-RS-r17 [1] NZP-CSI-RS-Pairing-r17 OPTIONAL, -- Need R
   pair2OfNZP-CSI-RS-r17 [2] NZP-CSI-RS-Pairing-r17 OPTIONAL -- Need R
}

-- TAG-NZP-CSI-RS-RESOURCEID-STOP
-- TAG-NZP-CSI-RS-RESOURCESET-START
NZP-CSI-RS-ResourceSet ::= SEQUENCE {
   nzp-CSI-ResourceSetId [0] NZP-CSI-RS-ResourceSetId,
   nzp-CSI-RS-Resources [1] SEQUENCE (SIZE (1..maxNrofNZP-CSI-RS-ResourcesPerSet)) OF NZP-CSI-RS-ResourceId,
   repetition [2] ENUMERATED { on(0), off(1) } OPTIONAL, -- Need S
   aperiodicTriggeringOffset [3] INTEGER (0..6) OPTIONAL, -- Need S
   trs-Info [4] ENUMERATED { true(0) } OPTIONAL,
   ...,
   [[
      aperiodicTriggeringOffset-r16 [5] INTEGER (0..31) OPTIONAL
   ]],
   [[
      pdc-Info-r17 [6] ENUMERATED { true(0) } OPTIONAL,
      cmrGroupingAndPairing-r17 [7] CMRGroupingAndPairing-r17 OPTIONAL,
      aperiodicTriggeringOffset-r17 [8] INTEGER (0..124) OPTIONAL,
      aperiodicTriggeringOffsetL2-r17 [9] INTEGER (0..31) OPTIONAL
   ]]
}

-- TAG-CSI-FREQUENCYOCCUPATION-STOP
-- TAG-CSI-IM-RESOURCE-START
CSI-IM-Resource ::= SEQUENCE {
   csi-IM-ResourceId [0] CSI-IM-ResourceId,
   csi-IM-ResourceElementPattern [1] EXPLICIT CHOICE {
      pattern0 [0] SEQUENCE {
         subcarrierLocation-p0 [0] ENUMERATED { s0(0), s2(1), s4(2), s6(3), 
            s8(4), s10(5) },
         symbolLocation-p0 [1] INTEGER (0..12)
      },
      pattern1 [1] SEQUENCE {
         subcarrierLocation-p1 [0] ENUMERATED { s0(0), s4(1), s8(2) },
         symbolLocation-p1 [1] INTEGER (0..13)
      }
   } OPTIONAL, -- Need M
   freqBand [2] CSI-FrequencyOccupation OPTIONAL, -- Need M
   periodicityAndOffset [3] EXPLICIT CSI-ResourcePeriodicityAndOffset OPTIONAL,
   ...
}

-- TAG-CSI-IM-RESOURCEID-STOP
-- TAG-CSI-IM-RESOURCESET-START
CSI-IM-ResourceSet ::= SEQUENCE {
   csi-IM-ResourceSetId [0] CSI-IM-ResourceSetId,
   csi-IM-Resources [1] SEQUENCE (SIZE (1..maxNrofCSI-IM-ResourcesPerSet)) OF CSI-IM-ResourceId,
   ...
}

-- TAG-CSI-SEMIPERSISTENTONPUSCHTRIGGERSTATELIST-STOP
-- TAG-CSI-SSB-RESOURCESET-START
CSI-SSB-ResourceSet ::= SEQUENCE {
   csi-SSB-ResourceSetId [0] CSI-SSB-ResourceSetId,
   csi-SSB-ResourceList [1] SEQUENCE (SIZE (1..maxNrofCSI-SSB-ResourcePerSet)) OF SSB-Index,
   ...,
   [[
      servingAdditionalPCIList-r17 [2] SEQUENCE (SIZE (1..maxNrofCSI-SSB-ResourcePerSet)) OF 
         ServingAdditionalPCIIndex-r17 OPTIONAL
   ]]
}

-- TAG-CSI-REPORTCONFIGID-STOP
-- TAG-CSI-RESOURCECONFIG-START
CSI-ResourceConfig ::= SEQUENCE {
   csi-ResourceConfigId [0] CSI-ResourceConfigId,
   csi-RS-ResourceSetList [1] EXPLICIT CHOICE {
      nzp-CSI-RS-SSB [0] SEQUENCE {
         nzp-CSI-RS-ResourceSetList [0] SEQUENCE (SIZE (1..maxNrofNZP-CSI-RS-ResourceSetsPerConfig)) OF 
            NZP-CSI-RS-ResourceSetId OPTIONAL,
                                                                                                                                         -- Need R
         csi-SSB-ResourceSetList [1] SEQUENCE (SIZE (1..maxNrofCSI-SSB-ResourceSetsPerConfig)) OF 
            CSI-SSB-ResourceSetId OPTIONAL -- Need R
      },
      csi-IM-ResourceSetList [1] SEQUENCE (SIZE (1..maxNrofCSI-IM-ResourceSetsPerConfig)) OF CSI-IM-ResourceSetId
   },
   bwp-Id [2] BWP-Id,
   resourceType [3] ENUMERATED { aperiodic(0), semiPersistent(1), periodic(2) }
      ,
   ...,
   [[
      csi-SSB-ResourceSetListExt-r17 [4] CSI-SSB-ResourceSetId OPTIONAL
   ]]
}

CSI-ReportPeriodicityAndOffset ::= CHOICE {
   slots4 [0] INTEGER (0..3),
   slots5 [1] INTEGER (0..4),
   slots8 [2] INTEGER (0..7),
   slots10 [3] INTEGER (0..9),
   slots16 [4] INTEGER (0..15),
   slots20 [5] INTEGER (0..19),
   slots40 [6] INTEGER (0..39),
   slots80 [7] INTEGER (0..79),
   slots160 [8] INTEGER (0..159),
   slots320 [9] INTEGER (0..319)
}

PUCCH-CSI-Resource ::= SEQUENCE {
   uplinkBandwidthPartId [0] BWP-Id,
   pucch-Resource [1] PUCCH-ResourceId
}

-- TAG-CLI-RSSI-RANGE-STOP
-- TAG-CODEBOOKCONFIG-START
CodebookConfig ::= SEQUENCE {
   codebookType [0] EXPLICIT CHOICE {
      type1 [0] SEQUENCE {
         subType [0] EXPLICIT CHOICE {
            typeI-SinglePanel [0] SEQUENCE {
               nrOfAntennaPorts [0] EXPLICIT CHOICE {
                  two [0] SEQUENCE {
                     twoTX-CodebookSubsetRestriction [0] BIT STRING  (SIZE (6))
                  },
                  moreThanTwo [1] SEQUENCE {
                     n1-n2 [0] EXPLICIT CHOICE {
                        two-one-TypeI-SinglePanel-Restriction [0] BIT STRING  (
                           SIZE (8)),
                        two-two-TypeI-SinglePanel-Restriction [1] BIT STRING  (
                           SIZE (64)),
                        four-one-TypeI-SinglePanel-Restriction [2] BIT STRING 
                            (SIZE (16)),
                        three-two-TypeI-SinglePanel-Restriction [3] BIT STRING 
                            (SIZE (96)),
                        six-one-TypeI-SinglePanel-Restriction [4] BIT STRING  (
                           SIZE (24)),
                        four-two-TypeI-SinglePanel-Restriction [5] BIT STRING 
                            (SIZE (128)),
                        eight-one-TypeI-SinglePanel-Restriction [6] BIT STRING 
                            (SIZE (32)),
                        four-three-TypeI-SinglePanel-Restriction [7] 
                           BIT STRING  (SIZE (192)),
                        six-two-TypeI-SinglePanel-Restriction [8] BIT STRING  (
                           SIZE (192)),
                        twelve-one-TypeI-SinglePanel-Restriction [9] 
                           BIT STRING  (SIZE (48)),
                        four-four-TypeI-SinglePanel-Restriction [10] 
                           BIT STRING  (SIZE (256)),
                        eight-two-TypeI-SinglePanel-Restriction [11] 
                           BIT STRING  (SIZE (256)),
                        sixteen-one-TypeI-SinglePanel-Restriction [12] 
                           BIT STRING  (SIZE (64))
                     },
                     typeI-SinglePanel-codebookSubsetRestriction-i2 [1] 
                        BIT STRING  (SIZE (16)) OPTIONAL -- Need R
                  }
               },
               typeI-SinglePanel-ri-Restriction [1] BIT STRING  (SIZE (8))
            },
            typeI-MultiPanel [1] SEQUENCE {
               ng-n1-n2 [0] EXPLICIT CHOICE {
                  two-two-one-TypeI-MultiPanel-Restriction [0] BIT STRING  (
                     SIZE (8)),
                  two-four-one-TypeI-MultiPanel-Restriction [1] BIT STRING  (
                     SIZE (16)),
                  four-two-one-TypeI-MultiPanel-Restriction [2] BIT STRING  (
                     SIZE (8)),
                  two-two-two-TypeI-MultiPanel-Restriction [3] BIT STRING  (
                     SIZE (64)),
                  two-eight-one-TypeI-MultiPanel-Restriction [4] BIT STRING  (
                     SIZE (32)),
                  four-four-one-TypeI-MultiPanel-Restriction [5] BIT STRING  (
                     SIZE (16)),
                  two-four-two-TypeI-MultiPanel-Restriction [6] BIT STRING  (
                     SIZE (128)),
                  four-two-two-TypeI-MultiPanel-Restriction [7] BIT STRING  (
                     SIZE (64))
               },
               ri-Restriction [1] BIT STRING  (SIZE (4))
            }
         },
         codebookMode [1] INTEGER (1..2)
      },
      type2 [1] SEQUENCE {
         subType [0] EXPLICIT CHOICE {
            typeII [0] SEQUENCE {
               n1-n2-codebookSubsetRestriction [0] EXPLICIT CHOICE {
                  two-one [0] BIT STRING  (SIZE (16)),
                  two-two [1] BIT STRING  (SIZE (43)),
                  four-one [2] BIT STRING  (SIZE (32)),
                  three-two [3] BIT STRING  (SIZE (59)),
                  six-one [4] BIT STRING  (SIZE (48)),
                  four-two [5] BIT STRING  (SIZE (75)),
                  eight-one [6] BIT STRING  (SIZE (64)),
                  four-three [7] BIT STRING  (SIZE (107)),
                  six-two [8] BIT STRING  (SIZE (107)),
                  twelve-one [9] BIT STRING  (SIZE (96)),
                  four-four [10] BIT STRING  (SIZE (139)),
                  eight-two [11] BIT STRING  (SIZE (139)),
                  sixteen-one [12] BIT STRING  (SIZE (128))
               },
               typeII-RI-Restriction [1] BIT STRING  (SIZE (2))
            },
            typeII-PortSelection [1] SEQUENCE {
               portSelectionSamplingSize [0] ENUMERATED { n1(0), n2(1), n3(2), 
                  n4(3) } OPTIONAL, -- Need R
               typeII-PortSelectionRI-Restriction [1] BIT STRING  (SIZE (2))
            }
         },
         phaseAlphabetSize [1] ENUMERATED { n4(0), n8(1) },
         subbandAmplitude [2] BOOLEAN,
         numberOfBeams [3] ENUMERATED { two(0), three(1), four(2) }
      }
   }
}

PortIndexFor8Ranks ::= CHOICE {
   portIndex8 [0] SEQUENCE {
      rank1-8 [0] PortIndex8 OPTIONAL, -- Need R
      rank2-8 [1] SEQUENCE (SIZE (2)) OF PortIndex8 OPTIONAL, -- Need R
      rank3-8 [2] SEQUENCE (SIZE (3)) OF PortIndex8 OPTIONAL, -- Need R
      rank4-8 [3] SEQUENCE (SIZE (4)) OF PortIndex8 OPTIONAL, -- Need R
      rank5-8 [4] SEQUENCE (SIZE (5)) OF PortIndex8 OPTIONAL, -- Need R
      rank6-8 [5] SEQUENCE (SIZE (6)) OF PortIndex8 OPTIONAL, -- Need R
      rank7-8 [6] SEQUENCE (SIZE (7)) OF PortIndex8 OPTIONAL, -- Need R
      rank8-8 [7] SEQUENCE (SIZE (8)) OF PortIndex8 OPTIONAL -- Need R
   },
   portIndex4 [1] SEQUENCE {
      rank1-4 [0] PortIndex4 OPTIONAL, -- Need R
      rank2-4 [1] SEQUENCE (SIZE (2)) OF PortIndex4 OPTIONAL, -- Need R
      rank3-4 [2] SEQUENCE (SIZE (3)) OF PortIndex4 OPTIONAL, -- Need R
      rank4-4 [3] SEQUENCE (SIZE (4)) OF PortIndex4 OPTIONAL -- Need R
   },
   portIndex2 [2] SEQUENCE {
      rank1-2 [0] PortIndex2 OPTIONAL, -- Need R
      rank2-2 [1] SEQUENCE (SIZE (2)) OF PortIndex2 OPTIONAL -- Need R
   },
   portIndex1 [3] NULL
}

CodebookConfig-r16 ::= SEQUENCE {
   codebookType [0] EXPLICIT CHOICE {
      type2 [0] SEQUENCE {
         subType [0] EXPLICIT CHOICE {
            typeII-r16 [0] SEQUENCE {
               n1-n2-codebookSubsetRestriction-r16 [0] EXPLICIT CHOICE {
                  two-one [0] BIT STRING  (SIZE (16)),
                  two-two [1] BIT STRING  (SIZE (43)),
                  four-one [2] BIT STRING  (SIZE (32)),
                  three-two [3] BIT STRING  (SIZE (59)),
                  six-one [4] BIT STRING  (SIZE (48)),
                  four-two [5] BIT STRING  (SIZE (75)),
                  eight-one [6] BIT STRING  (SIZE (64)),
                  four-three [7] BIT STRING  (SIZE (107)),
                  six-two [8] BIT STRING  (SIZE (107)),
                  twelve-one [9] BIT STRING  (SIZE (96)),
                  four-four [10] BIT STRING  (SIZE (139)),
                  eight-two [11] BIT STRING  (SIZE (139)),
                  sixteen-one [12] BIT STRING  (SIZE (128))
               },
               typeII-RI-Restriction-r16 [1] BIT STRING  (SIZE (4))
            },
            typeII-PortSelection-r16 [1] SEQUENCE {
               portSelectionSamplingSize-r16 [0] ENUMERATED { n1(0), n2(1), 
                  n3(2), n4(3) },
               typeII-PortSelectionRI-Restriction-r16 [1] BIT STRING  (SIZE (4))
            }
         },
         numberOfPMI-SubbandsPerCQI-Subband-r16 [1] INTEGER (1..2),
         paramCombination-r16 [2] INTEGER (1..8)
      }
   }
}

CodebookConfig-r17 ::= SEQUENCE {
   codebookType [0] EXPLICIT CHOICE {
      type1 [0] SEQUENCE {
         typeI-SinglePanel-Group1-r17 [0] SEQUENCE {
            nrOfAntennaPorts [0] EXPLICIT CHOICE {
               two [0] SEQUENCE {
                  twoTX-CodebookSubsetRestriction1-r17 [0] BIT STRING  (SIZE (6)
                     )
               },
               moreThanTwo [1] SEQUENCE {
                  n1-n2 [0] EXPLICIT CHOICE {
                     two-one-TypeI-SinglePanel-Restriction1-r17 [0] BIT STRING 
                         (SIZE (8)),
                     two-two-TypeI-SinglePanel-Restriction1-r17 [1] BIT STRING 
                         (SIZE (64)),
                     four-one-TypeI-SinglePanel-Restriction1-r17 [2] 
                        BIT STRING  (SIZE (16)),
                     three-two-TypeI-SinglePanel-Restriction1-r17 [3] 
                        BIT STRING  (SIZE (96)),
                     six-one-TypeI-SinglePanel-Restriction1-r17 [4] BIT STRING 
                         (SIZE (24)),
                     four-two-TypeI-SinglePanel-Restriction1-r17 [5] 
                        BIT STRING  (SIZE (128)),
                     eight-one-TypeI-SinglePanel-Restriction1-r17 [6] 
                        BIT STRING  (SIZE (32)),
                     four-three-TypeI-SinglePanel-Restriction1-r17 [7] 
                        BIT STRING  (SIZE (192)),
                     six-two-TypeI-SinglePanel-Restriction1-r17 [8] BIT STRING 
                         (SIZE (192)),
                     twelve-one-TypeI-SinglePanel-Restriction1-r17 [9] 
                        BIT STRING  (SIZE (48)),
                     four-four-TypeI-SinglePanel-Restriction1-r17 [10] 
                        BIT STRING  (SIZE (256)),
                     eight-two-TypeI-SinglePanel-Restriction1-r17 [11] 
                        BIT STRING  (SIZE (256)),
                     sixteen-one-TypeI-SinglePanel-Restriction1-r17 [12] 
                        BIT STRING  (SIZE (64))
                  }
               }
            }
         } OPTIONAL, -- Need R
         typeI-SinglePanel-Group2-r17 [1] SEQUENCE {
            nrOfAntennaPorts [0] EXPLICIT CHOICE {
               two [0] SEQUENCE {
                  twoTX-CodebookSubsetRestriction2-r17 [0] BIT STRING  (SIZE (6)
                     )
               },
               moreThanTwo [1] SEQUENCE {
                  n1-n2 [0] EXPLICIT CHOICE {
                     two-one-TypeI-SinglePanel-Restriction2-r17 [0] BIT STRING 
                         (SIZE (8)),
                     two-two-TypeI-SinglePanel-Restriction2-r17 [1] BIT STRING 
                         (SIZE (64)),
                     four-one-TypeI-SinglePanel-Restriction2-r17 [2] 
                        BIT STRING  (SIZE (16)),
                     three-two-TypeI-SinglePanel-Restriction2-r17 [3] 
                        BIT STRING  (SIZE (96)),
                     six-one-TypeI-SinglePanel-Restriction2-r17 [4] BIT STRING 
                         (SIZE (24)),
                     four-two-TypeI-SinglePanel-Restriction2-r17 [5] 
                        BIT STRING  (SIZE (128)),
                     eight-one-TypeI-SinglePanel-Restriction2-r17 [6] 
                        BIT STRING  (SIZE (32)),
                     four-three-TypeI-SinglePanel-Restriction2-r17 [7] 
                        BIT STRING  (SIZE (192)),
                     six-two-TypeI-SinglePanel-Restriction2-r17 [8] BIT STRING 
                         (SIZE (192)),
                     twelve-one-TypeI-SinglePanel-Restriction2-r17 [9] 
                        BIT STRING  (SIZE (48)),
                     four-four-TypeI-SinglePanel-Restriction2-r17 [10] 
                        BIT STRING  (SIZE (256)),
                     eight-two-TypeI-SinglePanel-Restriction2-r17 [11] 
                        BIT STRING  (SIZE (256)),
                     sixteen-one-TypeI-SinglePanel-Restriction2-r17 [12] 
                        BIT STRING  (SIZE (64))
                  }
               }
            }
         } OPTIONAL, -- Need R
         typeI-SinglePanel-ri-RestrictionSTRP-r17 [2] BIT STRING  (SIZE (8))
             OPTIONAL, -- Need R
         typeI-SinglePanel-ri-RestrictionSDM-r17 [3] BIT STRING  (SIZE (4))
             OPTIONAL -- Need R
      },
      type2 [1] SEQUENCE {
         typeII-PortSelection-r17 [0] SEQUENCE {
            paramCombination-r17 [0] INTEGER (1..8),
            valueOfN-r17 [1] ENUMERATED { n2(0), n4(1) } OPTIONAL, -- Need R
            numberOfPMI-SubbandsPerCQI-Subband-r17 [2] INTEGER (1..2) OPTIONAL, -- Need R
            typeII-PortSelectionRI-Restriction-r17 [3] BIT STRING  (SIZE (4))
         }
      }
   }
}

CodebookConfig-v1730 ::= SEQUENCE {
   codebookType [0] EXPLICIT CHOICE {
      type1 [0] SEQUENCE {
         codebookMode [0] INTEGER (1..2) OPTIONAL -- Need R
      }
   }
}

-- TAG-CSI-MEASCONFIG-STOP
-- TAG-CSI-REPORTCONFIG-START
CSI-ReportConfig ::= SEQUENCE {
   reportConfigId [0] CSI-ReportConfigId,
   carrier [1] ServCellIndex OPTIONAL, -- Need S
   resourcesForChannelMeasurement [2] CSI-ResourceConfigId,
   csi-IM-ResourcesForInterference [3] CSI-ResourceConfigId OPTIONAL, -- Need R
   nzp-CSI-RS-ResourcesForInterference [4] CSI-ResourceConfigId OPTIONAL, -- Need R
   reportConfigType [5] EXPLICIT CHOICE {
      periodic [0] SEQUENCE {
         reportSlotConfig [0] EXPLICIT CSI-ReportPeriodicityAndOffset,
         pucch-CSI-ResourceList [1] SEQUENCE (SIZE (1..maxNrofBWPs)) OF PUCCH-CSI-Resource
      },
      semiPersistentOnPUCCH [1] SEQUENCE {
         reportSlotConfig [0] EXPLICIT CSI-ReportPeriodicityAndOffset,
         pucch-CSI-ResourceList [1] SEQUENCE (SIZE (1..maxNrofBWPs)) OF PUCCH-CSI-Resource
      },
      semiPersistentOnPUSCH [2] SEQUENCE {
         reportSlotConfig [0] ENUMERATED { sl5(0), sl10(1), sl20(2), sl40(3), 
            sl80(4), sl160(5), sl320(6) },
         reportSlotOffsetList [1] SEQUENCE (SIZE (1..maxNrofUL-Allocations)) OF INTEGER (0..32),
         p0alpha [2] P0-PUSCH-AlphaSetId
      },
      aperiodic [3] SEQUENCE {
         reportSlotOffsetList [0] SEQUENCE (SIZE (1..maxNrofUL-Allocations)) OF INTEGER (0..32)
      }
   },
   reportQuantity [6] EXPLICIT CHOICE {
      none [0] NULL,
      cri-RI-PMI-CQI [1] NULL,
      cri-RI-i1 [2] NULL,
      cri-RI-i1-CQI [3] SEQUENCE {
         pdsch-BundleSizeForCSI [0] ENUMERATED { n2(0), n4(1) } OPTIONAL -- Need S
      },
      cri-RI-CQI [4] NULL,
      cri-RSRP [5] NULL,
      ssb-Index-RSRP [6] NULL,
      cri-RI-LI-PMI-CQI [7] NULL
   },
   reportFreqConfiguration [7] SEQUENCE {
      cqi-FormatIndicator [0] ENUMERATED { widebandCQI(0), subbandCQI(1) }
          OPTIONAL, -- Need R
      pmi-FormatIndicator [1] ENUMERATED { widebandPMI(0), subbandPMI(1) }
          OPTIONAL, -- Need R
      csi-ReportingBand [2] EXPLICIT CHOICE {
         subbands3 [0] BIT STRING  (SIZE (3)),
         subbands4 [1] BIT STRING  (SIZE (4)),
         subbands5 [2] BIT STRING  (SIZE (5)),
         subbands6 [3] BIT STRING  (SIZE (6)),
         subbands7 [4] BIT STRING  (SIZE (7)),
         subbands8 [5] BIT STRING  (SIZE (8)),
         subbands9 [6] BIT STRING  (SIZE (9)),
         subbands10 [7] BIT STRING  (SIZE (10)),
         subbands11 [8] BIT STRING  (SIZE (11)),
         subbands12 [9] BIT STRING  (SIZE (12)),
         subbands13 [10] BIT STRING  (SIZE (13)),
         subbands14 [11] BIT STRING  (SIZE (14)),
         subbands15 [12] BIT STRING  (SIZE (15)),
         subbands16 [13] BIT STRING  (SIZE (16)),
         subbands17 [14] BIT STRING  (SIZE (17)),
         subbands18 [15] BIT STRING  (SIZE (18)),
         ...,
         subbands19-v1530 [16] BIT STRING  (SIZE (19))
      } OPTIONAL -- Need S
   } OPTIONAL, -- Need R
   timeRestrictionForChannelMeasurements [8] ENUMERATED { configured(0), 
      notConfigured(1) },
   timeRestrictionForInterferenceMeasurements [9] ENUMERATED { configured(0), 
      notConfigured(1) },
   codebookConfig [10] CodebookConfig OPTIONAL, -- Need R
   dummy [11] ENUMERATED { n1(0), n2(1) } OPTIONAL, -- Need R
   groupBasedBeamReporting [12] EXPLICIT CHOICE {
      enabled [0] NULL,
      disabled [1] SEQUENCE {
         nrofReportedRS [0] ENUMERATED { n1(0), n2(1), n3(2), n4(3) } OPTIONAL -- Need S
      }
   },
   cqi-Table [13] ENUMERATED { table1(0), table2(1), table3(2), table4-r17(3) }
       OPTIONAL, -- Need R
   subbandSize [14] ENUMERATED { value1(0), value2(1) },
   non-PMI-PortIndication [15] SEQUENCE (SIZE (1..maxNrofNZP-CSI-RS-ResourcesPerConfig)) OF PortIndexFor8Ranks
       OPTIONAL,
   ...,
   [[
      semiPersistentOnPUSCH-v1530 [16] SEQUENCE {
         reportSlotConfig-v1530 [0] ENUMERATED { sl4(0), sl8(1), sl16(2) }
      } OPTIONAL
   ]],
   [[
      semiPersistentOnPUSCH-v1610 [17] SEQUENCE {
         reportSlotOffsetListDCI-0-2-r16 [0] SEQUENCE (SIZE (1..maxNrofUL-Allocations-r16)) OF INTEGER (0
            ..32) OPTIONAL, -- Need R
         reportSlotOffsetListDCI-0-1-r16 [1] SEQUENCE (SIZE (1..maxNrofUL-Allocations-r16)) OF INTEGER (0
            ..32) OPTIONAL -- Need R
      } OPTIONAL,
      aperiodic-v1610 [18] SEQUENCE {
         reportSlotOffsetListDCI-0-2-r16 [0] SEQUENCE (SIZE (1..maxNrofUL-Allocations-r16)) OF INTEGER (0
            ..32) OPTIONAL, -- Need R
         reportSlotOffsetListDCI-0-1-r16 [1] SEQUENCE (SIZE (1..maxNrofUL-Allocations-r16)) OF INTEGER (0
            ..32) OPTIONAL -- Need R
      } OPTIONAL,
      reportQuantity-r16 [19] EXPLICIT CHOICE {
         cri-SINR-r16 [0] NULL,
         ssb-Index-SINR-r16 [1] NULL
      } OPTIONAL,
      codebookConfig-r16 [20] CodebookConfig-r16 OPTIONAL
   ]],
   [[
      cqi-BitsPerSubband-r17 [21] ENUMERATED { bits4(0) } OPTIONAL,
      groupBasedBeamReporting-v1710 [22] SEQUENCE {
         nrofReportedGroups-r17 [0] ENUMERATED { n1(0), n2(1), n3(2), n4(3) }
      } OPTIONAL,
      codebookConfig-r17 [23] CodebookConfig-r17 OPTIONAL,
      sharedCMR-r17 [24] ENUMERATED { enable(0) } OPTIONAL,
      csi-ReportMode-r17 [25] ENUMERATED { mode1(0), mode2(1) } OPTIONAL,
      numberOfSingleTRP-CSI-Mode1-r17 [26] ENUMERATED { n0(0), n1(1), n2(2) }
          OPTIONAL,
      reportQuantity-r17 [27] EXPLICIT CHOICE {
         cri-RSRP-Index-r17 [0] NULL,
         ssb-Index-RSRP-Index-r17 [1] NULL,
         cri-SINR-Index-r17 [2] NULL,
         ssb-Index-SINR-Index-r17 [3] NULL
      } OPTIONAL
   ]],
   [[
      semiPersistentOnPUSCH-v1720 [28] SEQUENCE {
         reportSlotOffsetList-r17 [0] SEQUENCE (SIZE (1..maxNrofUL-Allocations-r16)) OF INTEGER (0..128)
             OPTIONAL, -- Need R
         reportSlotOffsetListDCI-0-2-r17 [1] SEQUENCE (SIZE (1..maxNrofUL-Allocations-r16)) OF INTEGER (0
            ..128) OPTIONAL, -- Need R
         reportSlotOffsetListDCI-0-1-r17 [2] SEQUENCE (SIZE (1..maxNrofUL-Allocations-r16)) OF INTEGER (0
            ..128) OPTIONAL -- Need R
      } OPTIONAL,
      aperiodic-v1720 [29] SEQUENCE {
         reportSlotOffsetList-r17 [0] SEQUENCE (SIZE (1..maxNrofUL-Allocations-r16)) OF INTEGER (0..128)
             OPTIONAL, -- Need R
         reportSlotOffsetListDCI-0-2-r17 [1] SEQUENCE (SIZE (1..maxNrofUL-Allocations-r16)) OF INTEGER (0
            ..128) OPTIONAL, -- Need R
         reportSlotOffsetListDCI-0-1-r17 [2] SEQUENCE (SIZE (1..maxNrofUL-Allocations-r16)) OF INTEGER (0
            ..128) OPTIONAL -- Need R
      } OPTIONAL
   ]],
   [[
      codebookConfig-v1730 [30] CodebookConfig-v1730 OPTIONAL
   ]]
}

CSI-AssociatedReportConfigInfo ::= SEQUENCE {
   reportConfigId [0] CSI-ReportConfigId,
   resourcesForChannel [1] EXPLICIT CHOICE {
      nzp-CSI-RS [0] SEQUENCE {
         resourceSet [0] INTEGER (1..maxNrofNZP-CSI-RS-ResourceSetsPerConfig),
         qcl-info [1] SEQUENCE (SIZE (1..maxNrofAP-CSI-RS-ResourcesPerSet)) OF TCI-StateId OPTIONAL
                                                                                                                   -- Cond Aperiodic
      },
      csi-SSB-ResourceSet [1] INTEGER (1..maxNrofCSI-SSB-ResourceSetsPerConfig)
   },
   csi-IM-ResourcesForInterference [2] INTEGER (1..maxNrofCSI-IM-ResourceSetsPerConfig) OPTIONAL, -- Cond CSI-IM-ForInterference
   nzp-CSI-RS-ResourcesForInterference [3] INTEGER (1..maxNrofNZP-CSI-RS-ResourceSetsPerConfig) OPTIONAL,
   ...,
   [[
      resourcesForChannel2-r17 [4] EXPLICIT CHOICE {
         nzp-CSI-RS2-r17 [0] SEQUENCE {
            resourceSet2-r17 [0] INTEGER (1..maxNrofNZP-CSI-RS-ResourceSetsPerConfig),
            qcl-info2-r17 [1] SEQUENCE (SIZE (1..maxNrofAP-CSI-RS-ResourcesPerSet)) OF TCI-StateId OPTIONAL
                                                                                                             -- Cond Aperiodic
         },
         csi-SSB-ResourceSet2-r17 [1] INTEGER (1..maxNrofCSI-SSB-ResourceSetsPerConfigExt)
      } OPTIONAL,
      csi-SSB-ResourceSetExt [5] INTEGER (1..maxNrofCSI-SSB-ResourceSetsPerConfigExt) OPTIONAL
   ]]
}

CSI-AperiodicTriggerState ::= SEQUENCE {
   associatedReportConfigInfoList [0] SEQUENCE (SIZE (1..maxNrofReportConfigPerAperiodicTrigger)) OF 
      CSI-AssociatedReportConfigInfo,
   ...,
   [[
      ap-CSI-MultiplexingMode-r17 [1] ENUMERATED { enabled(0) } OPTIONAL
   ]]
}

-- TAG-CROSSCARRIERSCHEDULINGCONFIG-STOP
-- TAG-CSI-APERIODICTRIGGERSTATELIST-START
CSI-AperiodicTriggerStateList ::= SEQUENCE (SIZE (1..maxNrOfCSI-AperiodicTriggers)) OF 
   CSI-AperiodicTriggerState

CSI-SemiPersistentOnPUSCH-TriggerState ::= SEQUENCE {
   associatedReportConfigInfo [0] CSI-ReportConfigId,
   ...,
   [[
      sp-CSI-MultiplexingMode-r17 [1] ENUMERATED { enabled(0) } OPTIONAL
   ]]
}

-- TAG-CSI-RS-RESOURCEMAPPING-STOP
-- TAG-CSI-SEMIPERSISTENTONPUSCHTRIGGERSTATELIST-START
CSI-SemiPersistentOnPUSCH-TriggerStateList ::= SEQUENCE (SIZE (1..maxNrOfSemiPersistentPUSCH-Triggers)) OF 
   CSI-SemiPersistentOnPUSCH-TriggerState

-- TAG-RXTXTIMEDIFF-STOP
-- TAG-SCELLACTIVATIONRS-CONFIG-START
SCellActivationRS-Config-r17 ::= SEQUENCE {
   scellActivationRS-Id-r17 [0] SCellActivationRS-ConfigId-r17,
   resourceSet-r17 [1] NZP-CSI-RS-ResourceSetId,
   gapBetweenBursts-r17 [2] INTEGER (2..31) OPTIONAL, -- Need R
   qcl-Info-r17 [3] TCI-StateId,
   ...
}

-- TAG-CSI-IM-RESOURCESETID-STOP
-- TAG-CSI-MEASCONFIG-START
CSI-MeasConfig ::= SEQUENCE {
   nzp-CSI-RS-ResourceToAddModList [0] SEQUENCE (SIZE (1..maxNrofNZP-CSI-RS-Resources)) OF 
      NZP-CSI-RS-Resource OPTIONAL, -- Need N
   nzp-CSI-RS-ResourceToReleaseList [1] SEQUENCE (SIZE (1..maxNrofNZP-CSI-RS-Resources)) OF 
      NZP-CSI-RS-ResourceId OPTIONAL, -- Need N
   nzp-CSI-RS-ResourceSetToAddModList [2] SEQUENCE (SIZE (1..maxNrofNZP-CSI-RS-ResourceSets)) OF 
      NZP-CSI-RS-ResourceSet OPTIONAL,
                                                                                                                             -- Need N
   nzp-CSI-RS-ResourceSetToReleaseList [3] SEQUENCE (SIZE (1..maxNrofNZP-CSI-RS-ResourceSets)) OF 
      NZP-CSI-RS-ResourceSetId OPTIONAL,
                                                                                                                             -- Need N
   csi-IM-ResourceToAddModList [4] SEQUENCE (SIZE (1..maxNrofCSI-IM-Resources)) OF CSI-IM-Resource
       OPTIONAL, -- Need N
   csi-IM-ResourceToReleaseList [5] SEQUENCE (SIZE (1..maxNrofCSI-IM-Resources)) OF CSI-IM-ResourceId
       OPTIONAL, -- Need N
   csi-IM-ResourceSetToAddModList [6] SEQUENCE (SIZE (1..maxNrofCSI-IM-ResourceSets)) OF 
      CSI-IM-ResourceSet OPTIONAL, -- Need N
   csi-IM-ResourceSetToReleaseList [7] SEQUENCE (SIZE (1..maxNrofCSI-IM-ResourceSets)) OF 
      CSI-IM-ResourceSetId OPTIONAL, -- Need N
   csi-SSB-ResourceSetToAddModList [8] SEQUENCE (SIZE (1..maxNrofCSI-SSB-ResourceSets)) OF 
      CSI-SSB-ResourceSet OPTIONAL, -- Need N
   csi-SSB-ResourceSetToReleaseList [9] SEQUENCE (SIZE (1..maxNrofCSI-SSB-ResourceSets)) OF 
      CSI-SSB-ResourceSetId OPTIONAL, -- Need N
   csi-ResourceConfigToAddModList [10] SEQUENCE (SIZE (1..maxNrofCSI-ResourceConfigurations)) OF 
      CSI-ResourceConfig OPTIONAL,
                                                                                                                             -- Need N
   csi-ResourceConfigToReleaseList [11] SEQUENCE (SIZE (1..maxNrofCSI-ResourceConfigurations)) OF 
      CSI-ResourceConfigId OPTIONAL,
                                                                                                                             -- Need N
   csi-ReportConfigToAddModList [12] SEQUENCE (SIZE (1..maxNrofCSI-ReportConfigurations)) OF CSI-ReportConfig
       OPTIONAL, -- Need N
   csi-ReportConfigToReleaseList [13] SEQUENCE (SIZE (1..maxNrofCSI-ReportConfigurations)) OF 
      CSI-ReportConfigId OPTIONAL,
                                                                                                                             -- Need N
   reportTriggerSize [14] INTEGER (0..6) OPTIONAL, -- Need M
   aperiodicTriggerStateList [15] EXPLICIT CHOICE {
      release [0] NULL,
      setup [1] EXPLICIT CSI-AperiodicTriggerStateList
   } OPTIONAL, -- Need M
   semiPersistentOnPUSCH-TriggerStateList [16] EXPLICIT CHOICE {
      release [0] NULL,
      setup [1] EXPLICIT CSI-SemiPersistentOnPUSCH-TriggerStateList
   } OPTIONAL,
   ...,
   [[
      reportTriggerSizeDCI-0-2-r16 [17] INTEGER (0..6) OPTIONAL
   ]],
   [[
      sCellActivationRS-ConfigToAddModList-r17 [18] SEQUENCE (SIZE (1..maxNrofSCellActRS-r17)) OF 
         SCellActivationRS-Config-r17 OPTIONAL,
      sCellActivationRS-ConfigToReleaseList-r17 [19] SEQUENCE (SIZE (1..maxNrofSCellActRS-r17)) OF 
         SCellActivationRS-ConfigId-r17 OPTIONAL
   ]]
}

-- TAG-CONTROLRESOURCESETZERO-STOP
-- TAG-CROSSCARRIERSCHEDULINGCONFIG-START
CrossCarrierSchedulingConfig ::= SEQUENCE {
   schedulingCellInfo [0] EXPLICIT CHOICE {
      own [0] SEQUENCE {
                                                                               -- Cross carrier scheduling: scheduling cell
         cif-Presence [0] BOOLEAN
      },
      other [1] SEQUENCE {
                                                                               -- Cross carrier scheduling: scheduled cell
         schedulingCellId [0] ServCellIndex,
         cif-InSchedulingCell [1] INTEGER (1..7)
      }
   },
   ...,
   [[
      carrierIndicatorSize-r16 [1] SEQUENCE {
         carrierIndicatorSizeDCI-1-2-r16 [0] INTEGER (0..3),
         carrierIndicatorSizeDCI-0-2-r16 [1] INTEGER (0..3)
      } OPTIONAL,
      enableDefaultBeamForCCS-r16 [2] ENUMERATED { enabled(0) } OPTIONAL
   ]],
   [[
      ccs-BlindDetectionSplit-r17 [3] ENUMERATED { oneSeventh(0), 
         threeFourteenth(1), twoSeventh(2), threeSeventh(3), oneHalf(4), 
         fourSeventh(5), fiveSeventh(6), spare1(7) } OPTIONAL
   ]]
}

TDD-UL-DL-SlotConfig-IAB-MT-r16 ::= SEQUENCE {
   slotIndex-r16 [0] TDD-UL-DL-SlotIndex,
   symbols-IAB-MT-r16 [1] EXPLICIT CHOICE {
      allDownlink-r16 [0] NULL,
      allUplink-r16 [1] NULL,
      explicit-r16 [2] SEQUENCE {
         nrofDownlinkSymbols-r16 [0] INTEGER (1..maxNrofSymbols-1) OPTIONAL, -- Need S
         nrofUplinkSymbols-r16 [1] INTEGER (1..maxNrofSymbols-1) OPTIONAL -- Need S
      },
      explicit-IAB-MT-r16 [3] SEQUENCE {
         nrofDownlinkSymbols-r16 [0] INTEGER (1..maxNrofSymbols-1) OPTIONAL, -- Need S
         nrofUplinkSymbols-r16 [1] INTEGER (1..maxNrofSymbols-1) OPTIONAL -- Need S
      }
   }
}

TDD-UL-DL-ConfigDedicated-IAB-MT-r16 ::= SEQUENCE {
   slotSpecificConfigurationsToAddModList-IAB-MT-r16 [0] SEQUENCE (SIZE (1..maxNrofSlots)
      ) OF TDD-UL-DL-SlotConfig-IAB-MT-r16 OPTIONAL, -- Need N
   slotSpecificConfigurationsToReleaseList-IAB-MT-r16 [1] SEQUENCE (SIZE (1..maxNrofSlots)
      ) OF TDD-UL-DL-SlotIndex OPTIONAL,
   ...
}

WithinActiveTimeConfig-r16 ::= SEQUENCE {
   firstWithinActiveTimeBWP-Id-r16 [0] BWP-Id OPTIONAL, -- Need M
   dormancyGroupWithinActiveTime-r16 [1] DormancyGroupID-r16 OPTIONAL -- Need R
}

OutsideActiveTimeConfig-r16 ::= SEQUENCE {
   firstOutsideActiveTimeBWP-Id-r16 [0] BWP-Id OPTIONAL, -- Need M
   dormancyGroupOutsideActiveTime-r16 [1] DormancyGroupID-r16 OPTIONAL -- Need R
}

DormantBWP-Config-r16 ::= SEQUENCE {
   dormantBWP-Id-r16 [0] BWP-Id OPTIONAL, -- Need M
   withinActiveTimeConfig-r16 [1] EXPLICIT CHOICE {
      release [0] NULL,
      setup [1] EXPLICIT WithinActiveTimeConfig-r16
   } OPTIONAL, -- Need M
   outsideActiveTimeConfig-r16 [2] EXPLICIT CHOICE {
      release [0] NULL,
      setup [1] EXPLICIT OutsideActiveTimeConfig-r16
   } OPTIONAL -- Need M
}

DummyJ ::= SEQUENCE {
   maxEnergyDetectionThreshold-r16 [0] INTEGER (-85..-52),
   energyDetectionThresholdOffset-r16 [1] INTEGER (-20..-13),
   ul-toDL-COT-SharingED-Threshold-r16 [2] INTEGER (-85..-52) OPTIONAL, -- Need R
   absenceOfAnyOtherTechnology-r16 [3] ENUMERATED { true(0) } OPTIONAL -- Need R
}

GuardBand-r16 ::= SEQUENCE {
   startCRB-r16 [0] INTEGER (0..274),
   nrofCRBs-r16 [1] INTEGER (0..15)
}

IntraCellGuardBandsPerSCS-r16 ::= SEQUENCE {
   guardBandSCS-r16 [0] SubcarrierSpacing,
   intraCellGuardBands-r16 [1] SEQUENCE (SIZE (1..4)) OF GuardBand-r16
}

LTE-CRS-PatternList-r16 ::= SEQUENCE (SIZE (1..maxLTE-CRS-Patterns-r16)) OF RateMatchPatternLTE-CRS

ChannelAccessConfig-r16 ::= SEQUENCE {
   energyDetectionConfig-r16 [0] EXPLICIT CHOICE {
      maxEnergyDetectionThreshold-r16 [0] INTEGER (-85..-52),
      energyDetectionThresholdOffset-r16 [1] INTEGER (-13..20)
   } OPTIONAL, -- Need R
   ul-toDL-COT-SharingED-Threshold-r16 [1] INTEGER (-85..-52) OPTIONAL, -- Need R
   absenceOfAnyOtherTechnology-r16 [2] ENUMERATED { true(0) } OPTIONAL -- Need R
}

NR-DL-PRS-Periodicity-and-ResourceSetSlotOffset-r17 ::= CHOICE {
   scs15-r17 [0] EXPLICIT CHOICE {
      n4-r17 [0] INTEGER (0..3),
      n5-r17 [1] INTEGER (0..4),
      n8-r17 [2] INTEGER (0..7),
      n10-r17 [3] INTEGER (0..9),
      n16-r17 [4] INTEGER (0..15),
      n20-r17 [5] INTEGER (0..19),
      n32-r17 [6] INTEGER (0..31),
      n40-r17 [7] INTEGER (0..39),
      n64-r17 [8] INTEGER (0..63),
      n80-r17 [9] INTEGER (0..79),
      n160-r17 [10] INTEGER (0..159),
      n320-r17 [11] INTEGER (0..319),
      n640-r17 [12] INTEGER (0..639),
      n1280-r17 [13] INTEGER (0..1279),
      n2560-r17 [14] INTEGER (0..2559),
      n5120-r17 [15] INTEGER (0..5119),
      n10240-r17 [16] INTEGER (0..10239),
      ...
   },
   scs30-r17 [1] EXPLICIT CHOICE {
      n8-r17 [0] INTEGER (0..7),
      n10-r17 [1] INTEGER (0..9),
      n16-r17 [2] INTEGER (0..15),
      n20-r17 [3] INTEGER (0..19),
      n32-r17 [4] INTEGER (0..31),
      n40-r17 [5] INTEGER (0..39),
      n64-r17 [6] INTEGER (0..63),
      n80-r17 [7] INTEGER (0..79),
      n128-r17 [8] INTEGER (0..127),
      n160-r17 [9] INTEGER (0..159),
      n320-r17 [10] INTEGER (0..319),
      n640-r17 [11] INTEGER (0..639),
      n1280-r17 [12] INTEGER (0..1279),
      n2560-r17 [13] INTEGER (0..2559),
      n5120-r17 [14] INTEGER (0..5119),
      n10240-r17 [15] INTEGER (0..10239),
      n20480-r17 [16] INTEGER (0..20479),
      ...
   },
   scs60-r17 [2] EXPLICIT CHOICE {
      n16-r17 [0] INTEGER (0..15),
      n20-r17 [1] INTEGER (0..19),
      n32-r17 [2] INTEGER (0..31),
      n40-r17 [3] INTEGER (0..39),
      n64-r17 [4] INTEGER (0..63),
      n80-r17 [5] INTEGER (0..79),
      n128-r17 [6] INTEGER (0..127),
      n160-r17 [7] INTEGER (0..159),
      n256-r17 [8] INTEGER (0..255),
      n320-r17 [9] INTEGER (0..319),
      n640-r17 [10] INTEGER (0..639),
      n1280-r17 [11] INTEGER (0..1279),
      n2560-r17 [12] INTEGER (0..2559),
      n5120-r17 [13] INTEGER (0..5119),
      n10240-r17 [14] INTEGER (0..10239),
      n20480-r17 [15] INTEGER (0..20479),
      n40960-r17 [16] INTEGER (0..40959),
      ...
   },
   scs120-r17 [3] EXPLICIT CHOICE {
      n32-r17 [0] INTEGER (0..31),
      n40-r17 [1] INTEGER (0..39),
      n64-r17 [2] INTEGER (0..63),
      n80-r17 [3] INTEGER (0..79),
      n128-r17 [4] INTEGER (0..127),
      n160-r17 [5] INTEGER (0..159),
      n256-r17 [6] INTEGER (0..255),
      n320-r17 [7] INTEGER (0..319),
      n512-r17 [8] INTEGER (0..511),
      n640-r17 [9] INTEGER (0..639),
      n1280-r17 [10] INTEGER (0..1279),
      n2560-r17 [11] INTEGER (0..2559),
      n5120-r17 [12] INTEGER (0..5119),
      n10240-r17 [13] INTEGER (0..10239),
      n20480-r17 [14] INTEGER (0..20479),
      n40960-r17 [15] INTEGER (0..40959),
      n81920-r17 [16] INTEGER (0..81919),
      ...
   },
   ...
}

DL-PRS-QCL-Info-r17 ::= CHOICE {
   ssb-r17 [0] SEQUENCE {
      ssb-Index-r17 [0] INTEGER (0..63),
      rs-Type-r17 [1] ENUMERATED { typeC(0), typeD(1), typeC-plus-typeD(2) },
      ...
   },
   dl-PRS-r17 [1] SEQUENCE {
      qcl-DL-PRS-ResourceID-r17 [0] NR-DL-PRS-ResourceID-r17,
      ...
   },
   ...
}

NR-DL-PRS-Resource-r17 ::= SEQUENCE {
   nr-DL-PRS-ResourceID-r17 [0] NR-DL-PRS-ResourceID-r17,
   dl-PRS-SequenceID-r17 [1] INTEGER (0..4095),
   dl-PRS-CombSizeN-AndReOffset-r17 [2] EXPLICIT CHOICE {
      n2-r17 [0] INTEGER (0..1),
      n4-r17 [1] INTEGER (0..3),
      n6-r17 [2] INTEGER (0..5),
      n12-r17 [3] INTEGER (0..11),
      ...
   },
   dl-PRS-ResourceSlotOffset-r17 [3] INTEGER (0..maxNrofPRS-ResourceOffsetValue-1-r17),
   dl-PRS-ResourceSymbolOffset-r17 [4] INTEGER (0..12),
   dl-PRS-QCL-Info-r17 [5] EXPLICIT DL-PRS-QCL-Info-r17 OPTIONAL,
   ...
}

RepFactorAndTimeGap-r17 ::= SEQUENCE {
   repetitionFactor-r17 [0] ENUMERATED { n2(0), n4(1), n6(2), n8(3), n16(4), 
      n32(5), spare2(6), spare1(7) },
   timeGap-r17 [1] ENUMERATED { s1(0), s2(1), s4(2), s8(3), s16(4), s32(5), 
      spare2(6), spare1(7) }
}

NR-DL-PRS-PDC-ResourceSet-r17 ::= SEQUENCE {
   periodicityAndOffset-r17 [0] EXPLICIT 
      NR-DL-PRS-Periodicity-and-ResourceSetSlotOffset-r17,
   numSymbols-r17 [1] ENUMERATED { n2(0), n4(1), n6(2), n12(3), spare4(4), 
      spare3(5), spare2(6), spare1(7) },
   dl-PRS-ResourceBandwidth-r17 [2] INTEGER (1..63),
   dl-PRS-StartPRB-r17 [3] INTEGER (0..2176),
   resourceList-r17 [4] SEQUENCE (SIZE (1..maxNrofPRS-ResourcesPerSet-r17)) OF NR-DL-PRS-Resource-r17,
   repFactorAndTimeGap-r17 [5] RepFactorAndTimeGap-r17 OPTIONAL,
   ...
}

-- TAG-NPN-IDENTITYINFOLIST-STOP
-- TAG-NR-DL-PRS-PDC-INFO-START
NR-DL-PRS-PDC-Info-r17 ::= SEQUENCE {
   nr-DL-PRS-PDC-ResourceSet-r17 [0] NR-DL-PRS-PDC-ResourceSet-r17 OPTIONAL,
   ...
}

-- TAG-SEMISTATICCHANNELACCESSCONFIG-STOP
-- TAG-SEMISTATICCHANNELACCESSCONFIGUE-START
SemiStaticChannelAccessConfigUE-r17 ::= SEQUENCE {
   periodUE-r17 [0] ENUMERATED { ms1(0), ms2(1), ms2dot5(2), ms4(3), ms5(4), 
      ms10(5), spare2(6), spare1(7) },
   offsetUE-r17 [1] INTEGER (0..559)
}

SSB-MTC-AdditionalPCI-r17 ::= SEQUENCE {
   additionalPCIIndex-r17 [0] AdditionalPCIIndex-r17,
   additionalPCI-r17 [1] PhysCellId,
   periodicity-r17 [2] ENUMERATED { ms5(0), ms10(1), ms20(2), ms40(3), ms80(4)
      , ms160(5), spare2(6), spare1(7) },
   ssb-PositionsInBurst-r17 [3] EXPLICIT CHOICE {
      shortBitmap [0] BIT STRING  (SIZE (4)),
      mediumBitmap [1] BIT STRING  (SIZE (8)),
      longBitmap [2] BIT STRING  (SIZE (64))
   },
   ss-PBCH-BlockPower-r17 [4] INTEGER (-60..50)
}

P0AlphaSet-r17 ::= SEQUENCE {
   p0-r17 [0] INTEGER (-16..15) OPTIONAL, -- Need R
   alpha-r17 [1] Alpha OPTIONAL, -- Need S
   closedLoopIndex-r17 [2] ENUMERATED { i0(0), i1(1) }
}

-- TAG-UPLINKCONFIGCOMMONSIB-STOP
-- TAG-UPLINK-POWERCONTROL-START
Uplink-powerControl-r17 ::= SEQUENCE {
   ul-powercontrolId-r17 [0] Uplink-powerControlId-r17,
   p0AlphaSetforPUSCH-r17 [1] P0AlphaSet-r17 OPTIONAL, -- Need R
   p0AlphaSetforPUCCH-r17 [2] P0AlphaSet-r17 OPTIONAL, -- Need R
   p0AlphaSetforSRS-r17 [3] P0AlphaSet-r17 OPTIONAL -- Need R
}

MIMOParam-r17 ::= SEQUENCE {
   additionalPCI-ToAddModList-r17 [0] SEQUENCE (SIZE (1..maxNrofAdditionalPCI-r17)) OF 
      SSB-MTC-AdditionalPCI-r17 OPTIONAL, -- Need N
   additionalPCI-ToReleaseList-r17 [1] SEQUENCE (SIZE (1..maxNrofAdditionalPCI-r17)) OF 
      AdditionalPCIIndex-r17 OPTIONAL, -- Need N
   unifiedTCI-StateType-r17 [2] ENUMERATED { separate(0), joint(1) } OPTIONAL, -- Need R
   uplink-PowerControlToAddModList-r17 [3] SEQUENCE (SIZE (1..maxUL-TCI-r17)) OF 
      Uplink-powerControl-r17 OPTIONAL, -- Need N
   uplink-PowerControlToReleaseList-r17 [4] SEQUENCE (SIZE (1..maxUL-TCI-r17)) OF 
      Uplink-powerControlId-r17 OPTIONAL, -- Need N
   sfnSchemePDCCH-r17 [5] ENUMERATED { sfnSchemeA(0), sfnSchemeB(1) } OPTIONAL,
       -- Need R
   sfnSchemePDSCH-r17 [6] ENUMERATED { sfnSchemeA(0), sfnSchemeB(1) } OPTIONAL -- Need R
}

-- TAG-TAR-CONFIG-STOP
-- TAG-TCI-ACTIVATEDCONFIG-START
TCI-ActivatedConfig-r17 ::= SEQUENCE {
   pdcch-TCI-r17 [0] SEQUENCE (SIZE (1..5)) OF TCI-StateId,
   pdsch-TCI-r17 [1] BIT STRING  (SIZE (1..maxNrofTCI-States))
}

LTE-NeighCellsCRS-AssistInfo-r17 ::= SEQUENCE {
   neighCarrierBandwidthDL-r17 [0] ENUMERATED { n6(0), n15(1), n25(2), n50(3), 
      n75(4), n100(5), spare2(6), spare1(7) } OPTIONAL, -- Cond CRS-IM
   neighCarrierFreqDL-r17 [1] INTEGER (0..16383) OPTIONAL, -- Need S
   neighCellId-r17 [2] EUTRA-PhysCellId OPTIONAL, -- Need S
   neighCRS-muting-r17 [3] ENUMERATED { enabled(0) } OPTIONAL, -- Need R
   neighMBSFN-SubframeConfigList-r17 [4] EUTRA-MBSFN-SubframeConfigList
       OPTIONAL, -- Need S
   neighNrofCRS-Ports-r17 [5] ENUMERATED { n1(0), n2(1), n4(2) } OPTIONAL, -- Need S
   neighV-Shift-r17 [6] ENUMERATED { n0(0), n1(1), n2(2), n3(3), n4(4), n5(5) }
       OPTIONAL -- Cond NotCellID
}

-- TAG-LOGICALCHANNELIDENTITY-STOP
-- TAG-LTE-NEIGHCELLSCRS-ASSISTINFOLIST-START
LTE-NeighCellsCRS-AssistInfoList-r17 ::= SEQUENCE (SIZE (1..maxNrofCRS-IM-InterfCell-r17)) OF 
   LTE-NeighCellsCRS-AssistInfo-r17

-- TAG-SERVCELLINDEX-STOP
-- TAG-SERVINGCELLCONFIG-START
ServingCellConfig ::= SEQUENCE {
   tdd-UL-DL-ConfigurationDedicated [0] TDD-UL-DL-ConfigDedicated OPTIONAL, -- Cond TDD
   initialDownlinkBWP [1] BWP-DownlinkDedicated OPTIONAL, -- Need M
   downlinkBWP-ToReleaseList [2] SEQUENCE (SIZE (1..maxNrofBWPs)) OF BWP-Id OPTIONAL, -- Need N
   downlinkBWP-ToAddModList [3] SEQUENCE (SIZE (1..maxNrofBWPs)) OF BWP-Downlink OPTIONAL, -- Need N
   firstActiveDownlinkBWP-Id [4] BWP-Id OPTIONAL, -- Cond SyncAndCellAdd
   bwp-InactivityTimer [5] ENUMERATED { ms2(0), ms3(1), ms4(2), ms5(3), ms6(4)
      , ms8(5), ms10(6), ms20(7), ms30(8), ms40(9), ms50(10), ms60(11), 
      ms80(12), ms100(13), ms200(14), ms300(15), ms500(16), ms750(17), 
      ms1280(18), ms1920(19), ms2560(20), spare10(21), spare9(22), spare8(23), 
      spare7(24), spare6(25), spare5(26), spare4(27), spare3(28), spare2(29), 
      spare1(30) } OPTIONAL, --Need R
   defaultDownlinkBWP-Id [6] BWP-Id OPTIONAL, -- Need S
   uplinkConfig [7] UplinkConfig OPTIONAL, -- Need M
   supplementaryUplink [8] UplinkConfig OPTIONAL, -- Need M
   pdcch-ServingCellConfig [9] EXPLICIT CHOICE {
      release [0] NULL,
      setup [1] EXPLICIT PDCCH-ServingCellConfig
   } OPTIONAL, -- Need M
   pdsch-ServingCellConfig [10] EXPLICIT CHOICE {
      release [0] NULL,
      setup [1] EXPLICIT PDSCH-ServingCellConfig
   } OPTIONAL, -- Need M
   csi-MeasConfig [11] EXPLICIT CHOICE {
      release [0] NULL,
      setup [1] EXPLICIT CSI-MeasConfig
   } OPTIONAL, -- Need M
   sCellDeactivationTimer [12] ENUMERATED { ms20(0), ms40(1), ms80(2), ms160(3)
      , ms200(4), ms240(5), ms320(6), ms400(7), ms480(8), ms520(9), ms640(10), 
      ms720(11), ms840(12), ms1280(13), spare2(14), spare1(15) } OPTIONAL, -- Cond ServingCellWithoutPUCCH
   crossCarrierSchedulingConfig [13] CrossCarrierSchedulingConfig OPTIONAL, -- Need M
   tag-Id [14] TAG-Id,
   dummy1 [15] ENUMERATED { enabled(0) } OPTIONAL, -- Need R
   pathlossReferenceLinking [16] ENUMERATED { spCell(0), sCell(1) } OPTIONAL, -- Cond SCellOnly
   servingCellMO [17] MeasObjectId OPTIONAL,
   ...,
   [[
      lte-CRS-ToMatchAround [18] EXPLICIT CHOICE {
         release [0] NULL,
         setup [1] EXPLICIT RateMatchPatternLTE-CRS
      } OPTIONAL,
      rateMatchPatternToAddModList [19] SEQUENCE (SIZE (1..maxNrofRateMatchPatterns)) OF 
         RateMatchPattern OPTIONAL,
      rateMatchPatternToReleaseList [20] SEQUENCE (SIZE (1..maxNrofRateMatchPatterns)) OF 
         RateMatchPatternId OPTIONAL,
      downlinkChannelBW-PerSCS-List [21] SEQUENCE (SIZE (1..maxSCSs)) OF 
         SCS-SpecificCarrier OPTIONAL
   ]],
   [[
      supplementaryUplinkRelease-r16 [22] ENUMERATED { true(0) } OPTIONAL,
      tdd-UL-DL-ConfigurationDedicated-IAB-MT-r16 [23] 
         TDD-UL-DL-ConfigDedicated-IAB-MT-r16 OPTIONAL,
      dormantBWP-Config-r16 [24] EXPLICIT CHOICE {
         release [0] NULL,
         setup [1] EXPLICIT DormantBWP-Config-r16
      } OPTIONAL,
      ca-SlotOffset-r16 [25] EXPLICIT CHOICE {
         refSCS15kHz [0] INTEGER (-2..2),
         refSCS30KHz [1] INTEGER (-5..5),
         refSCS60KHz [2] INTEGER (-10..10),
         refSCS120KHz [3] INTEGER (-20..20)
      } OPTIONAL,
      dummy2 [26] EXPLICIT CHOICE {
         release [0] NULL,
         setup [1] EXPLICIT DummyJ
      } OPTIONAL,
      intraCellGuardBandsDL-List-r16 [27] SEQUENCE (SIZE (1..maxSCSs)) OF 
         IntraCellGuardBandsPerSCS-r16 OPTIONAL,
      intraCellGuardBandsUL-List-r16 [28] SEQUENCE (SIZE (1..maxSCSs)) OF 
         IntraCellGuardBandsPerSCS-r16 OPTIONAL,
      csi-RS-ValidationWithDCI-r16 [29] ENUMERATED { enabled(0) } OPTIONAL,
      lte-CRS-PatternList1-r16 [30] EXPLICIT CHOICE {
         release [0] NULL,
         setup [1] EXPLICIT LTE-CRS-PatternList-r16
      } OPTIONAL,
      lte-CRS-PatternList2-r16 [31] EXPLICIT CHOICE {
         release [0] NULL,
         setup [1] EXPLICIT LTE-CRS-PatternList-r16
      } OPTIONAL,
      crs-RateMatch-PerCORESETPoolIndex-r16 [32] ENUMERATED { enabled(0) }
          OPTIONAL,
      enableTwoDefaultTCI-States-r16 [33] ENUMERATED { enabled(0) } OPTIONAL,
      enableDefaultTCI-StatePerCoresetPoolIndex-r16 [34] ENUMERATED { 
         enabled(0) } OPTIONAL,
      enableBeamSwitchTiming-r16 [35] ENUMERATED { true(0) } OPTIONAL,
      cbg-TxDiffTBsProcessingType1-r16 [36] ENUMERATED { enabled(0) } OPTIONAL
         ,
      cbg-TxDiffTBsProcessingType2-r16 [37] ENUMERATED { enabled(0) } OPTIONAL
   ]],
   [[
      directionalCollisionHandling-r16 [38] ENUMERATED { enabled(0) } OPTIONAL
         ,
      channelAccessConfig-r16 [39] EXPLICIT CHOICE {
         release [0] NULL,
         setup [1] EXPLICIT ChannelAccessConfig-r16
      } OPTIONAL
   ]],
   [[
      nr-dl-PRS-PDC-Info-r17 [40] EXPLICIT CHOICE {
         release [0] NULL,
         setup [1] EXPLICIT NR-DL-PRS-PDC-Info-r17
      } OPTIONAL,
      semiStaticChannelAccessConfigUE-r17 [41] EXPLICIT CHOICE {
         release [0] NULL,
         setup [1] EXPLICIT SemiStaticChannelAccessConfigUE-r17
      } OPTIONAL,
      mimoParam-r17 [42] EXPLICIT CHOICE {
         release [0] NULL,
         setup [1] EXPLICIT MIMOParam-r17
      } OPTIONAL,
      channelAccessMode2-r17 [43] ENUMERATED { enabled(0) } OPTIONAL,
      timeDomainHARQ-BundlingType1-r17 [44] ENUMERATED { enabled(0) } OPTIONAL
         ,
      nrofHARQ-BundlingGroups-r17 [45] ENUMERATED { n1(0), n2(1), n4(2) }
          OPTIONAL,
      fdmed-ReceptionMulticast-r17 [46] ENUMERATED { true(0) } OPTIONAL,
      moreThanOneNackOnlyMode-r17 [47] ENUMERATED { mode2(0) } OPTIONAL,
      tci-ActivatedConfig-r17 [48] TCI-ActivatedConfig-r17 OPTIONAL,
      directionalCollisionHandling-DC-r17 [49] ENUMERATED { enabled(0) }
          OPTIONAL,
      lte-NeighCellsCRS-AssistInfoList-r17 [50] EXPLICIT CHOICE {
         release [0] NULL,
         setup [1] EXPLICIT LTE-NeighCellsCRS-AssistInfoList-r17
      } OPTIONAL
   ]],
   [[
      lte-NeighCellsCRS-Assumptions-r17 [51] ENUMERATED { false(0) } OPTIONAL
   ]],
   [[
      crossCarrierSchedulingConfigRelease-r17 [52] ENUMERATED { true(0) }
          OPTIONAL
   ]],
   [[
      multiPDSCH-PerSlotType1-CB-r17 [53] ENUMERATED { enabled(0), disabled(1)
          } OPTIONAL
   ]]
}

GoodServingCellEvaluation-r17 ::= SEQUENCE {
   offset-r17 [0] ENUMERATED { db2(0), db4(1), db6(2), db8(3) } OPTIONAL -- Need S
}

DeactivatedSCG-Config-r17 ::= SEQUENCE {
   bfd-and-RLM-r17 [0] BOOLEAN,
   ...
}

-- Serving cell specific MAC and PHY parameters for a SpCell:
SpCellConfig ::= SEQUENCE {
   servCellIndex [0] ServCellIndex OPTIONAL, -- Cond SCG
   reconfigurationWithSync [1] ReconfigurationWithSync OPTIONAL, -- Cond ReconfWithSync
   rlf-TimersAndConstants [2] EXPLICIT CHOICE {
      release [0] NULL,
      setup [1] EXPLICIT RLF-TimersAndConstants
   } OPTIONAL, -- Need M
   rlmInSyncOutOfSyncThreshold [3] ENUMERATED { n1(0) } OPTIONAL, -- Need S
   spCellConfigDedicated [4] ServingCellConfig OPTIONAL,
   ...,
   [[
      lowMobilityEvaluationConnected-r17 [5] SEQUENCE {
         s-SearchDeltaP-Connected-r17 [0] ENUMERATED { dB3(0), dB6(1), dB9(2), 
            dB12(3), dB15(4), spare3(5), spare2(6), spare1(7) },
         t-SearchDeltaP-Connected-r17 [1] ENUMERATED { s5(0), s10(1), s20(2), 
            s30(3), s60(4), s120(5), s180(6), s240(7), s300(8), spare7(9), 
            spare6(10), spare5(11), spare4(12), spare3(13), spare2(14), 
            spare1(15) }
      } OPTIONAL,
      goodServingCellEvaluationRLM-r17 [6] GoodServingCellEvaluation-r17
          OPTIONAL,
      goodServingCellEvaluationBFD-r17 [7] GoodServingCellEvaluation-r17
          OPTIONAL,
      deactivatedSCG-Config-r17 [8] EXPLICIT CHOICE {
         release [0] NULL,
         setup [1] EXPLICIT DeactivatedSCG-Config-r17
      } OPTIONAL
   ]]
}

SCellConfig ::= SEQUENCE {
   sCellIndex [0] SCellIndex,
   sCellConfigCommon [1] ServingCellConfigCommon OPTIONAL, -- Cond SCellAdd
   sCellConfigDedicated [2] ServingCellConfig OPTIONAL,
   ...,
   [[
      smtc [3] SSB-MTC OPTIONAL
   ]],
   [[
      sCellState-r16 [4] ENUMERATED { activated(0) } OPTIONAL,
      secondaryDRX-GroupConfig-r16 [5] ENUMERATED { true(0) } OPTIONAL
   ]],
   [[
      preConfGapStatus-r17 [6] BIT STRING  (SIZE (maxNrofGapId-r17)) OPTIONAL,
      goodServingCellEvaluationBFD-r17 [7] GoodServingCellEvaluation-r17
          OPTIONAL,
      sCellSIB20-r17 [8] EXPLICIT CHOICE {
         release [0] NULL,
         setup [1] EXPLICIT SCellSIB20-r17
      } OPTIONAL
   ]],
   [[
      plmn-IdentityInfoList-r17 [9] EXPLICIT CHOICE {
         release [0] NULL,
         setup [1] EXPLICIT PLMN-IdentityInfoList
      } OPTIONAL,
      npn-IdentityInfoList-r17 [10] EXPLICIT CHOICE {
         release [0] NULL,
         setup [1] EXPLICIT NPN-IdentityInfoList-r16
      } OPTIONAL
   ]]
}

-- TAG-BETAOFFSETSCROSSPRI-STOP
-- TAG-BHLOGICALCHANNELIDENTITY-START
BH-LogicalChannelIdentity-r16 ::= CHOICE {
   bh-LogicalChannelIdentity-r16 [0] LogicalChannelIdentity,
   bh-LogicalChannelIdentityExt-r16 [1] BH-LogicalChannelIdentity-Ext-r16
}

-- TAG-BHLOGICALCHANNELIDENTITYEXT-STOP
-- TAG-BHRLCCHANNELCONFIG-START
BH-RLC-ChannelConfig-r16 ::= SEQUENCE {
   bh-LogicalChannelIdentity-r16 [0] EXPLICIT BH-LogicalChannelIdentity-r16
       OPTIONAL, -- Cond LCH-SetupOnly
   bh-RLC-ChannelID-r16 [1] BH-RLC-ChannelID-r16,
   reestablishRLC-r16 [2] ENUMERATED { true(0) } OPTIONAL, -- Need N
   rlc-Config-r16 [3] EXPLICIT RLC-Config OPTIONAL, -- Cond LCH-Setup
   mac-LogicalChannelConfig-r16 [4] LogicalChannelConfig OPTIONAL,
   ...
}

-- TAG-UPLINK-POWERCONTROL-STOP
-- TAG-UU-RELAYRLC-CHANNELCONFIG-START
Uu-RelayRLC-ChannelConfig-r17 ::= SEQUENCE {
   uu-LogicalChannelIdentity-r17 [0] LogicalChannelIdentity OPTIONAL, -- Cond RelayLCH-SetupOnly
   uu-RelayRLC-ChannelID-r17 [1] Uu-RelayRLC-ChannelID-r17,
   reestablishRLC-r17 [2] ENUMERATED { true(0) } OPTIONAL, -- Need N
   rlc-Config-r17 [3] EXPLICIT RLC-Config OPTIONAL, -- Cond RelayLCH-Setup
   mac-LogicalChannelConfig-r17 [4] LogicalChannelConfig OPTIONAL,
   ...
}

IAB-ResourceConfig-r17 ::= SEQUENCE {
   iab-ResourceConfigID-r17 [0] IAB-ResourceConfigID-r17,
   slotList-r17 [1] SEQUENCE (SIZE (1..5120)) OF INTEGER (0..5119) OPTIONAL, -- Need M
   periodicitySlotList-r17 [2] ENUMERATED { ms0p5(0), ms0p625(1), ms1(2), 
      ms1p25(3), ms2(4), ms2p5(5), ms5(6), ms10(7), ms20(8), ms40(9), ms80(10)
      , ms160(11) } OPTIONAL, -- Need M
   slotListSubcarrierSpacing-r17 [3] SubcarrierSpacing OPTIONAL,
   ...
}

CarrierState-r17 ::= CHOICE {
   deActivated-r17 [0] NULL,
   activeBWP-r17 [1] INTEGER (0..maxNrofBWPs)
}

CC-State-r17 ::= SEQUENCE {
   dlCarrier-r17 [0] EXPLICIT CarrierState-r17 OPTIONAL, -- Need N
   ulCarrier-r17 [1] EXPLICIT CarrierState-r17 OPTIONAL -- Need N
}

IntraBandCC-Combination-r17 ::= SEQUENCE (SIZE (1..maxNrofServingCells)) OF CC-State-r17

IntraBandCC-CombinationReqList-r17 ::= SEQUENCE {
   servCellIndexList-r17 [0] SEQUENCE (SIZE (1..maxNrofServingCells)) OF ServCellIndex,
   cc-CombinationList-r17 [1] SEQUENCE (SIZE (1..maxNrofReqComDC-Location-r17)) OF 
      IntraBandCC-Combination-r17
}

ReportUplinkTxDirectCurrentMoreCarrier-r17 ::= SEQUENCE (SIZE (1..maxSimultaneousBands)) OF 
   IntraBandCC-CombinationReqList-r17

-- TAG-CELLACCESSRELATEDINFOEUTRA-EPC-STOP
-- TAG-CELLGROUPCONFIG-START
-- Configuration of one Cell-Group:
CellGroupConfig ::= SEQUENCE {
   cellGroupId [0] CellGroupId,
   rlc-BearerToAddModList [1] SEQUENCE (SIZE (1..maxLC-ID)) OF RLC-BearerConfig OPTIONAL
      , -- Need N
   rlc-BearerToReleaseList [2] SEQUENCE (SIZE (1..maxLC-ID)) OF LogicalChannelIdentity
       OPTIONAL, -- Need N
   mac-CellGroupConfig [3] MAC-CellGroupConfig OPTIONAL, -- Need M
   physicalCellGroupConfig [4] PhysicalCellGroupConfig OPTIONAL, -- Need M
   spCellConfig [5] SpCellConfig OPTIONAL, -- Need M
   sCellToAddModList [6] SEQUENCE (SIZE (1..maxNrofSCells)) OF SCellConfig OPTIONAL, -- Need N
   sCellToReleaseList [7] SEQUENCE (SIZE (1..maxNrofSCells)) OF SCellIndex OPTIONAL,
   ...,
   [[
      reportUplinkTxDirectCurrent [8] ENUMERATED { true(0) } OPTIONAL
   ]],
   [[
      bap-Address-r16 [9] BIT STRING  (SIZE (10)) OPTIONAL,
      bh-RLC-ChannelToAddModList-r16 [10] SEQUENCE (SIZE (1..maxBH-RLC-ChannelID-r16)) OF 
         BH-RLC-ChannelConfig-r16 OPTIONAL,
      bh-RLC-ChannelToReleaseList-r16 [11] SEQUENCE (SIZE (1..maxBH-RLC-ChannelID-r16)) OF 
         BH-RLC-ChannelID-r16 OPTIONAL,
      f1c-TransferPath-r16 [12] ENUMERATED { lte(0), nr(1), both(2) } OPTIONAL
         ,
      simultaneousTCI-UpdateList1-r16 [13] SEQUENCE (SIZE (1..maxNrofServingCellsTCI-r16)) OF 
         ServCellIndex OPTIONAL,
      simultaneousTCI-UpdateList2-r16 [14] SEQUENCE (SIZE (1..maxNrofServingCellsTCI-r16)) OF 
         ServCellIndex OPTIONAL,
      simultaneousSpatial-UpdatedList1-r16 [15] SEQUENCE (SIZE (1..maxNrofServingCellsTCI-r16)) OF 
         ServCellIndex OPTIONAL,
      simultaneousSpatial-UpdatedList2-r16 [16] SEQUENCE (SIZE (1..maxNrofServingCellsTCI-r16)) OF 
         ServCellIndex OPTIONAL,
      uplinkTxSwitchingOption-r16 [17] ENUMERATED { switchedUL(0), dualUL(1) }
          OPTIONAL,
      uplinkTxSwitchingPowerBoosting-r16 [18] ENUMERATED { enabled(0) }
          OPTIONAL
   ]],
   [[
      reportUplinkTxDirectCurrentTwoCarrier-r16 [19] ENUMERATED { true(0) }
          OPTIONAL
   ]],
   [[
      f1c-TransferPathNRDC-r17 [20] ENUMERATED { mcg(0), scg(1), both(2) }
          OPTIONAL,
      uplinkTxSwitching-2T-Mode-r17 [21] ENUMERATED { enabled(0) } OPTIONAL,
      uplinkTxSwitching-DualUL-TxState-r17 [22] ENUMERATED { oneT(0), twoT(1) }
          OPTIONAL,
      uu-RelayRLC-ChannelToAddModList-r17 [23] SEQUENCE (SIZE (1..maxUu-RelayRLC-ChannelID-r17)) OF 
         Uu-RelayRLC-ChannelConfig-r17 OPTIONAL,
      uu-RelayRLC-ChannelToReleaseList-r17 [24] SEQUENCE (SIZE (1..maxUu-RelayRLC-ChannelID-r17)) OF 
         Uu-RelayRLC-ChannelID-r17 OPTIONAL,
      simultaneousU-TCI-UpdateList1-r17 [25] SEQUENCE (SIZE (1..maxNrofServingCellsTCI-r16)) OF 
         ServCellIndex OPTIONAL,
      simultaneousU-TCI-UpdateList2-r17 [26] SEQUENCE (SIZE (1..maxNrofServingCellsTCI-r16)) OF 
         ServCellIndex OPTIONAL,
      simultaneousU-TCI-UpdateList3-r17 [27] SEQUENCE (SIZE (1..maxNrofServingCellsTCI-r16)) OF 
         ServCellIndex OPTIONAL,
      simultaneousU-TCI-UpdateList4-r17 [28] SEQUENCE (SIZE (1..maxNrofServingCellsTCI-r16)) OF 
         ServCellIndex OPTIONAL,
      rlc-BearerToReleaseListExt-r17 [29] SEQUENCE (SIZE (1..maxLC-ID)) OF 
         LogicalChannelIdentityExt-r17 OPTIONAL,
      iab-ResourceConfigToAddModList-r17 [30] SEQUENCE (SIZE (1..maxNrofIABResourceConfig-r17)) OF 
         IAB-ResourceConfig-r17 OPTIONAL,
      iab-ResourceConfigToReleaseList-r17 [31] SEQUENCE (SIZE (1..maxNrofIABResourceConfig-r17)) OF 
         IAB-ResourceConfigID-r17 OPTIONAL
   ]],
   [[
      reportUplinkTxDirectCurrentMoreCarrier-r17 [32] 
         ReportUplinkTxDirectCurrentMoreCarrier-r17 OPTIONAL
   ]],
   [[
      prioSCellPRACH-OverSP-PeriodicSRS-r17 [33] ENUMERATED { enabled(0) }
          OPTIONAL
   ]]
}

MAC-MainConfigSL-r16 ::= SEQUENCE {
   sl-BSR-Config-r16 [0] BSR-Config OPTIONAL, -- Need M
   ul-PrioritizationThres-r16 [1] INTEGER (1..16) OPTIONAL, -- Need M
   sl-PrioritizationThres-r16 [2] INTEGER (1..8) OPTIONAL,
   ...
}

SL-PeriodCG-r16 ::= CHOICE {
   sl-PeriodCG1-r16 [0] ENUMERATED { ms100(0), ms200(1), ms300(2), ms400(3), 
      ms500(4), ms600(5), ms700(6), ms800(7), ms900(8), ms1000(9), spare6(10), 
      spare5(11), spare4(12), spare3(13), spare2(14), spare1(15) },
   sl-PeriodCG2-r16 [1] INTEGER (1..99)
}

SL-CG-MaxTransNum-r16 ::= SEQUENCE {
   sl-Priority-r16 [0] INTEGER (1..8),
   sl-MaxTransNum-r16 [1] INTEGER (1..32)
}

SL-CG-MaxTransNumList-r16 ::= SEQUENCE (SIZE (1..8)) OF SL-CG-MaxTransNum-r16

-- TAG-SL-CONFIGDEDICATEDNR-STOP
-- TAG-SL-CONFIGUREDGRANTCONFIG-START
SL-ConfiguredGrantConfig-r16 ::= SEQUENCE {
   sl-ConfigIndexCG-r16 [0] SL-ConfigIndexCG-r16,
   sl-PeriodCG-r16 [1] EXPLICIT SL-PeriodCG-r16 OPTIONAL, -- Need M
   sl-NrOfHARQ-Processes-r16 [2] INTEGER (1..16) OPTIONAL, -- Need M
   sl-HARQ-ProcID-offset-r16 [3] INTEGER (0..15) OPTIONAL, -- Need M
   sl-CG-MaxTransNumList-r16 [4] SL-CG-MaxTransNumList-r16 OPTIONAL, -- Need M
   rrc-ConfiguredSidelinkGrant-r16 [5] SEQUENCE {
      sl-TimeResourceCG-Type1-r16 [0] INTEGER (0..496) OPTIONAL, -- Need M
      sl-StartSubchannelCG-Type1-r16 [1] INTEGER (0..26) OPTIONAL, -- Need M
      sl-FreqResourceCG-Type1-r16 [2] INTEGER (0..6929) OPTIONAL, -- Need M
      sl-TimeOffsetCG-Type1-r16 [3] INTEGER (0..7999) OPTIONAL, -- Need R
      sl-N1PUCCH-AN-r16 [4] PUCCH-ResourceId OPTIONAL, -- Need M
      sl-PSFCH-ToPUCCH-CG-Type1-r16 [5] INTEGER (0..15) OPTIONAL, -- Need M
      sl-ResourcePoolID-r16 [6] SL-ResourcePoolID-r16 OPTIONAL, -- Need M
      sl-TimeReferenceSFN-Type1-r16 [7] ENUMERATED { sfn512(0) } OPTIONAL -- Need S
   } OPTIONAL,
   ...,
   [[
      sl-N1PUCCH-AN-Type2-r16 [6] PUCCH-ResourceId OPTIONAL
   ]]
}

SL-ConfiguredGrantConfigList-r16 ::= SEQUENCE {
   sl-ConfiguredGrantConfigToReleaseList-r16 [0] SEQUENCE (SIZE (1..maxNrofCG-SL-r16)) OF 
      SL-ConfigIndexCG-r16 OPTIONAL, -- Need N
   sl-ConfiguredGrantConfigToAddModList-r16 [1] SEQUENCE (SIZE (1..maxNrofCG-SL-r16)) OF 
      SL-ConfiguredGrantConfig-r16 OPTIONAL -- Need N
}

-- TAG-SL-RLC-CONFIG-STOP
-- TAG-SL-SCHEDULEDCONFIG-START
SL-ScheduledConfig-r16 ::= SEQUENCE {
   sl-RNTI-r16 [0] RNTI-Value,
   mac-MainConfigSL-r16 [1] MAC-MainConfigSL-r16 OPTIONAL, -- Need M
   sl-CS-RNTI-r16 [2] RNTI-Value OPTIONAL, -- Need M
   sl-PSFCH-ToPUCCH-r16 [3] SEQUENCE (SIZE (1..8)) OF INTEGER (0..15) OPTIONAL, -- Need M
   sl-ConfiguredGrantConfigList-r16 [4] SL-ConfiguredGrantConfigList-r16
       OPTIONAL,
   ...,
   [[
      sl-DCI-ToSL-Trans-r16 [5] SEQUENCE (SIZE (1..8)) OF INTEGER (1..32) OPTIONAL
   ]]
}

-- TAG-SL-THRES-RSRP-LIST-STOP
-- TAG-SL-TXPOWER-START
SL-TxPower-r16 ::= CHOICE {
   minusinfinity-r16 [0] NULL,
   txPower-r16 [1] INTEGER (-30..33)
}

SL-PSSCH-TxParameters-r16 ::= SEQUENCE {
   sl-MinMCS-PSSCH-r16 [0] INTEGER (0..27),
   sl-MaxMCS-PSSCH-r16 [1] INTEGER (0..31),
   sl-MinSubChannelNumPSSCH-r16 [2] INTEGER (1..27),
   sl-MaxSubchannelNumPSSCH-r16 [3] INTEGER (1..27),
   sl-MaxTxTransNumPSSCH-r16 [4] INTEGER (1..32),
   sl-MaxTxPower-r16 [5] EXPLICIT SL-TxPower-r16 OPTIONAL -- Cond CBR
}

SL-MinMaxMCS-Config-r16 ::= SEQUENCE {
   sl-MCS-Table-r16 [0] ENUMERATED { qam64(0), qam256(1), qam64LowSE(2) },
   sl-MinMCS-PSSCH-r16 [1] INTEGER (0..27),
   sl-MaxMCS-PSSCH-r16 [2] INTEGER (0..31)
}

SL-MinMaxMCS-List-r16 ::= SEQUENCE (SIZE (1..3)) OF SL-MinMaxMCS-Config-r16

SL-PSSCH-TxConfig-r16 ::= SEQUENCE {
   sl-TypeTxSync-r16 [0] SL-TypeTxSync-r16 OPTIONAL, -- Need R
   sl-ThresUE-Speed-r16 [1] ENUMERATED { kmph60(0), kmph80(1), kmph100(2), 
      kmph120(3), kmph140(4), kmph160(5), kmph180(6), kmph200(7) },
   sl-ParametersAboveThres-r16 [2] SL-PSSCH-TxParameters-r16,
   sl-ParametersBelowThres-r16 [3] SL-PSSCH-TxParameters-r16,
   ...,
   [[
      sl-ParametersAboveThres-v1650 [4] SL-MinMaxMCS-List-r16 OPTIONAL,
      sl-ParametersBelowThres-v1650 [5] SL-MinMaxMCS-List-r16 OPTIONAL
   ]]
}

-- TAG-SL-PSBCH-CONFIG-STOP
-- TAG-SL-PSSCH-TXCONFIGLIST-START
SL-PSSCH-TxConfigList-r16 ::= SEQUENCE (SIZE (1..maxPSSCH-TxConfig-r16)) OF SL-PSSCH-TxConfig-r16

SL-CBR-LevelsConfig-r16 ::= SEQUENCE (SIZE (1..maxCBR-Level-r16)) OF SL-CBR-r16

SL-CBR-PSSCH-TxConfig-r16 ::= SEQUENCE {
   sl-CR-Limit-r16 [0] INTEGER (0..10000) OPTIONAL, -- Need M
   sl-TxParameters-r16 [1] SL-PSSCH-TxParameters-r16 OPTIONAL -- Need M
}

-- TAG-SL-CBR-PRIORITYTXCONFIGLIST-STOP
-- TAG-SL-CBR-COMMONTXCONFIGLIST-START
SL-CBR-CommonTxConfigList-r16 ::= SEQUENCE {
   sl-CBR-RangeConfigList-r16 [0] SEQUENCE (SIZE (1..maxCBR-Config-r16)) OF 
      SL-CBR-LevelsConfig-r16 OPTIONAL, -- Need M
   sl-CBR-PSSCH-TxConfigList-r16 [1] SEQUENCE (SIZE (1..maxTxConfig-r16)) OF 
      SL-CBR-PSSCH-TxConfig-r16 OPTIONAL -- Need M
}

-- TAG-SL-TYPETXSYNC-STOP
-- TAG-SL-UE-SELECTEDCONFIG-START
SL-UE-SelectedConfig-r16 ::= SEQUENCE {
   sl-PSSCH-TxConfigList-r16 [0] SL-PSSCH-TxConfigList-r16 OPTIONAL, -- Need R
   sl-ProbResourceKeep-r16 [1] ENUMERATED { v0(0), v0dot2(1), v0dot4(2), 
      v0dot6(3), v0dot8(4) } OPTIONAL, -- Need R
   sl-ReselectAfter-r16 [2] ENUMERATED { n1(0), n2(1), n3(2), n4(3), n5(4), 
      n6(5), n7(6), n8(7), n9(8) } OPTIONAL, -- Need R
   sl-CBR-CommonTxConfigList-r16 [3] SL-CBR-CommonTxConfigList-r16 OPTIONAL, -- Need R
   ul-PrioritizationThres-r16 [4] INTEGER (1..16) OPTIONAL, -- Need R
   sl-PrioritizationThres-r16 [5] INTEGER (1..8) OPTIONAL,
   ...
}

-- TAG-SL-PDCP-CONFIG-STOP
-- TAG-SL-PSBCH-CONFIG-START
SL-PSBCH-Config-r16 ::= SEQUENCE {
   dl-P0-PSBCH-r16 [0] INTEGER (-16..15) OPTIONAL, -- Need M
   dl-Alpha-PSBCH-r16 [1] ENUMERATED { alpha0(0), alpha04(1), alpha05(2), 
      alpha06(3), alpha07(4), alpha08(5), alpha09(6), alpha1(7) } OPTIONAL,
   ...,
   [[
      dl-P0-PSBCH-r17 [2] INTEGER (-202..24) OPTIONAL
   ]]
}

SL-BWP-Generic-r16 ::= SEQUENCE {
   sl-BWP-r16 [0] BWP OPTIONAL, -- Need M
   sl-LengthSymbols-r16 [1] ENUMERATED { sym7(0), sym8(1), sym9(2), sym10(3), 
      sym11(4), sym12(5), sym13(6), sym14(7) } OPTIONAL, -- Need M
   sl-StartSymbol-r16 [2] ENUMERATED { sym0(0), sym1(1), sym2(2), sym3(3), 
      sym4(4), sym5(5), sym6(6), sym7(7) } OPTIONAL, -- Need M
   sl-PSBCH-Config-r16 [3] EXPLICIT CHOICE {
      release [0] NULL,
      setup [1] EXPLICIT SL-PSBCH-Config-r16
   } OPTIONAL, -- Need M
   sl-TxDirectCurrentLocation-r16 [4] INTEGER (0..3301) OPTIONAL,
   ...
}

SL-PSCCH-Config-r16 ::= SEQUENCE {
   sl-TimeResourcePSCCH-r16 [0] ENUMERATED { n2(0), n3(1) } OPTIONAL, -- Need M
   sl-FreqResourcePSCCH-r16 [1] ENUMERATED { n10(0), n12(1), n15(2), n20(3), 
      n25(4) } OPTIONAL, -- Need M
   sl-DMRS-ScrambleID-r16 [2] INTEGER (0..65535) OPTIONAL, -- Need M
   sl-NumReservedBits-r16 [3] INTEGER (2..4) OPTIONAL,
   ...
}

SL-PSSCH-Config-r16 ::= SEQUENCE {
   sl-PSSCH-DMRS-TimePatternList-r16 [0] SEQUENCE (SIZE (1..3)) OF INTEGER (2..4)
       OPTIONAL, -- Need M
   sl-BetaOffsets2ndSCI-r16 [1] SEQUENCE (SIZE (4)) OF SL-BetaOffsets-r16
       OPTIONAL, -- Need M
   sl-Scaling-r16 [2] ENUMERATED { f0p5(0), f0p65(1), f0p8(2), f1(3) } OPTIONAL
      ,
   ...
}

SL-PSFCH-Config-r16 ::= SEQUENCE {
   sl-PSFCH-Period-r16 [0] ENUMERATED { sl0(0), sl1(1), sl2(2), sl4(3) }
       OPTIONAL, -- Need M
   sl-PSFCH-RB-Set-r16 [1] BIT STRING  (SIZE (10..275)) OPTIONAL, -- Need M
   sl-NumMuxCS-Pair-r16 [2] ENUMERATED { n1(0), n2(1), n3(2), n6(3) } OPTIONAL,
       -- Need M
   sl-MinTimeGapPSFCH-r16 [3] ENUMERATED { sl2(0), sl3(1) } OPTIONAL, -- Need M
   sl-PSFCH-HopID-r16 [4] INTEGER (0..1023) OPTIONAL, -- Need M
   sl-PSFCH-CandidateResourceType-r16 [5] ENUMERATED { startSubCH(0), 
      allocSubCH(1) } OPTIONAL,
   ...
}

SL-SyncAllowed-r16 ::= SEQUENCE {
   gnss-Sync-r16 [0] ENUMERATED { true(0) } OPTIONAL, -- Need R
   gnbEnb-Sync-r16 [1] ENUMERATED { true(0) } OPTIONAL, -- Need R
   ue-Sync-r16 [2] ENUMERATED { true(0) } OPTIONAL -- Need R
}

SL-PTRS-Config-r16 ::= SEQUENCE {
   sl-PTRS-FreqDensity-r16 [0] SEQUENCE (SIZE (2)) OF INTEGER (1..276) OPTIONAL, -- Need M
   sl-PTRS-TimeDensity-r16 [1] SEQUENCE (SIZE (3)) OF INTEGER (0..29) OPTIONAL, -- Need M
   sl-PTRS-RE-Offset-r16 [2] ENUMERATED { offset01(0), offset10(1), offset11(2)
       } OPTIONAL,
   ...
}

SL-PriorityTxConfigIndex-r16 ::= SEQUENCE {
   sl-PriorityThreshold-r16 [0] INTEGER (1..8) OPTIONAL, -- Need M
   sl-DefaultTxConfigIndex-r16 [1] INTEGER (0..maxCBR-Level-1-r16) OPTIONAL, -- Need M
   sl-CBR-ConfigIndex-r16 [2] INTEGER (0..maxCBR-Config-1-r16) OPTIONAL, -- Need M
   sl-Tx-ConfigIndexList-r16 [3] SEQUENCE (SIZE (1..maxCBR-Level-r16)) OF SL-TxConfigIndex-r16
       OPTIONAL -- Need M
}

-- TAG-SL-BWP-POOLCONFIGCOMMON-STOP
-- TAG-SL-CBR-PRIORITYTXCONFIGLIST-START
SL-CBR-PriorityTxConfigList-r16 ::= SEQUENCE (SIZE (1..8)) OF 
   SL-PriorityTxConfigIndex-r16

-- TAG-SL-SYNCCONFIG-STOP
-- TAG-SL-THRES-RSRP-LIST-START
SL-Thres-RSRP-List-r16 ::= SEQUENCE (SIZE (64)) OF SL-Thres-RSRP-r16

SL-SelectionWindowConfig-r16 ::= SEQUENCE {
   sl-Priority-r16 [0] INTEGER (1..8),
   sl-SelectionWindow-r16 [1] ENUMERATED { n1(0), n5(1), n10(2), n20(3) }
}

SL-SelectionWindowList-r16 ::= SEQUENCE (SIZE (8)) OF 
   SL-SelectionWindowConfig-r16

SL-ResourceReservePeriod-r16 ::= CHOICE {
   sl-ResourceReservePeriod1-r16 [0] ENUMERATED { ms0(0), ms100(1), ms200(2), 
      ms300(3), ms400(4), ms500(5), ms600(6), ms700(7), ms800(8), ms900(9), 
      ms1000(10) },
   sl-ResourceReservePeriod2-r16 [1] INTEGER (1..99)
}

SL-PriorityTxConfigIndex-v1650 ::= SEQUENCE {
   sl-MCS-RangeList-r16 [0] SEQUENCE (SIZE (1..maxCBR-Level-r16)) OF SL-MinMaxMCS-List-r16
       OPTIONAL -- Need M
}

SL-CBR-PriorityTxConfigList-v1650 ::= SEQUENCE (SIZE (1..8)) OF 
   SL-PriorityTxConfigIndex-v1650

SL-UE-SelectedConfigRP-r16 ::= SEQUENCE {
   sl-CBR-PriorityTxConfigList-r16 [0] SL-CBR-PriorityTxConfigList-r16 OPTIONAL
      , -- Need M
   sl-Thres-RSRP-List-r16 [1] SL-Thres-RSRP-List-r16 OPTIONAL, -- Need M
   sl-MultiReserveResource-r16 [2] ENUMERATED { enabled(0) } OPTIONAL, -- Need M
   sl-MaxNumPerReserve-r16 [3] ENUMERATED { n2(0), n3(1) } OPTIONAL, -- Need M
   sl-SensingWindow-r16 [4] ENUMERATED { ms100(0), ms1100(1) } OPTIONAL, -- Need M
   sl-SelectionWindowList-r16 [5] SL-SelectionWindowList-r16 OPTIONAL, -- Need M
   sl-ResourceReservePeriodList-r16 [6] SEQUENCE (SIZE (1..16)) OF 
      SL-ResourceReservePeriod-r16 OPTIONAL, -- Need M
   sl-RS-ForSensing-r16 [7] ENUMERATED { pscch(0), pssch(1) },
   ...,
   [[
      sl-CBR-PriorityTxConfigList-v1650 [8] SL-CBR-PriorityTxConfigList-v1650
          OPTIONAL
   ]]
}

-- TAG-SL-UE-SELECTEDCONFIG-STOP
-- TAG-SL-ZONECONFIG-START
SL-ZoneConfig-r16 ::= SEQUENCE {
   sl-ZoneLength-r16 [0] ENUMERATED { m5(0), m10(1), m20(2), m30(3), m40(4), 
      m50(5), spare2(6), spare1(7) },
   ...
}

SL-ZoneConfigMCR-r16 ::= SEQUENCE {
   sl-ZoneConfigMCR-Index-r16 [0] INTEGER (0..15),
   sl-TransRange-r16 [1] ENUMERATED { m20(0), m50(1), m80(2), m100(3), m120(4)
      , m150(5), m180(6), m200(7), m220(8), m250(9), m270(10), m300(11), 
      m350(12), m370(13), m400(14), m420(15), m450(16), m480(17), m500(18), 
      m550(19), m600(20), m700(21), m1000(22), spare9(23), spare8(24), 
      spare7(25), spare6(26), spare5(27), spare4(28), spare3(29), spare2(30), 
      spare1(31) } OPTIONAL,
                                                                                                                          -- Need M
   sl-ZoneConfig-r16 [2] SL-ZoneConfig-r16 OPTIONAL,
   ...
}

SL-PowerControl-r16 ::= SEQUENCE {
   sl-MaxTransPower-r16 [0] INTEGER (-30..33),
   sl-Alpha-PSSCH-PSCCH-r16 [1] ENUMERATED { alpha0(0), alpha04(1), alpha05(2)
      , alpha06(3), alpha07(4), alpha08(5), alpha09(6), alpha1(7) } OPTIONAL, -- Need M
   dl-Alpha-PSSCH-PSCCH-r16 [2] ENUMERATED { alpha0(0), alpha04(1), alpha05(2)
      , alpha06(3), alpha07(4), alpha08(5), alpha09(6), alpha1(7) } OPTIONAL, -- Need S
   sl-P0-PSSCH-PSCCH-r16 [3] INTEGER (-16..15) OPTIONAL, -- Need S
   dl-P0-PSSCH-PSCCH-r16 [4] INTEGER (-16..15) OPTIONAL, -- Need M
   dl-Alpha-PSFCH-r16 [5] ENUMERATED { alpha0(0), alpha04(1), alpha05(2), 
      alpha06(3), alpha07(4), alpha08(5), alpha09(6), alpha1(7) } OPTIONAL, -- Need S
   dl-P0-PSFCH-r16 [6] INTEGER (-16..15) OPTIONAL,
   ...,
   [[
      dl-P0-PSSCH-PSCCH-r17 [7] INTEGER (-202..24) OPTIONAL,
      sl-P0-PSSCH-PSCCH-r17 [8] INTEGER (-202..24) OPTIONAL,
      dl-P0-PSFCH-r17 [9] INTEGER (-202..24) OPTIONAL
   ]]
}

SL-TxPercentageConfig-r16 ::= SEQUENCE {
   sl-Priority-r16 [0] INTEGER (1..8),
   sl-TxPercentage-r16 [1] ENUMERATED { p20(0), p35(1), p50(2) }
}

SL-TxPercentageList-r16 ::= SEQUENCE (SIZE (8)) OF SL-TxPercentageConfig-r16

-- TAG-SL-PAGINGIDENTITYREMOTEUE-STOP
-- TAG-SL-PBPS-CPS-CONFIG-START
SL-PBPS-CPS-Config-r17 ::= SEQUENCE {
   sl-AllowedResourceSelectionConfig-r17 [0] ENUMERATED { c1(0), c2(1), c3(2), 
      c4(3), c5(4), c6(5), c7(6) } OPTIONAL, -- Need M
   sl-MinNumCandidateSlotsPeriodic-r17 [1] INTEGER (1..32) OPTIONAL, -- Need M
   sl-PBPS-OccasionReservePeriodList-r17 [2] SEQUENCE (SIZE (1..16)) OF INTEGER (1
      ..16) OPTIONAL, -- Need M
   sl-Additional-PBPS-Occasion-r17 [3] ENUMERATED { monitored(0) } OPTIONAL, -- Need M
   sl-CPS-WindowPeriodic-r17 [4] INTEGER (5..30) OPTIONAL, -- Need M
   sl-MinNumCandidateSlotsAperiodic-r17 [5] INTEGER (1..32) OPTIONAL, -- Need M
   sl-MinNumRssiMeasurementSlots-r17 [6] INTEGER (1..800) OPTIONAL, -- Need M
   sl-DefaultCBR-RandomSelection-r17 [7] INTEGER (0..100) OPTIONAL, -- Need M
   sl-DefaultCBR-PartialSensing-r17 [8] INTEGER (0..100) OPTIONAL, -- Need M
   sl-CPS-WindowAperiodic-r17 [9] INTEGER (0..30) OPTIONAL, -- Need M
   sl-PartialSensingInactiveTime-r17 [10] ENUMERATED { enabled(0), disabled(1)
       } OPTIONAL,
   ...
}

SL-ThresholdRSRP-Condition1-B-1-r17 ::= SEQUENCE {
   sl-Priority-r17 [0] INTEGER (1..8),
   sl-ThresholdRSRP-Condition1-B-1-r17 [1] INTEGER (0..66)
}

SL-InterUE-CoordinationScheme1-r17 ::= SEQUENCE {
   sl-IUC-Explicit-r17 [0] ENUMERATED { enabled(0), disabled(1) } OPTIONAL, -- Need M
   sl-IUC-Condition-r17 [1] ENUMERATED { enabled(0), disabled(1) } OPTIONAL, -- Need M
   sl-Condition1-A-2-r17 [2] ENUMERATED { disabled(0) } OPTIONAL, -- Need M
   sl-ThresholdRSRP-Condition1-B-1-Option1List-r17 [3] SEQUENCE (SIZE (1..8)) OF 
      SL-ThresholdRSRP-Condition1-B-1-r17 OPTIONAL, -- Need M
   sl-ThresholdRSRP-Condition1-B-1-Option2List-r17 [4] SEQUENCE (SIZE (1..8)) OF 
      SL-ThresholdRSRP-Condition1-B-1-r17 OPTIONAL, -- Need M
   sl-ContainerCoordInfo-r17 [5] ENUMERATED { enabled(0), disabled(1) }
       OPTIONAL, -- Need M
   sl-ContainerRequest-r17 [6] ENUMERATED { enabled(0), disabled(1) } OPTIONAL,
       -- Need M
   sl-TriggerConditionCoordInfo-r17 [7] INTEGER (0..1) OPTIONAL, -- Need M
   sl-TriggerConditionRequest-r17 [8] INTEGER (0..1) OPTIONAL, -- Need M
   sl-PriorityCoordInfoExplicit-r17 [9] INTEGER (1..8) OPTIONAL, -- Need M
   sl-PriorityCoordInfoCondition-r17 [10] INTEGER (1..8) OPTIONAL, -- Need M
   sl-PriorityRequest-r17 [11] INTEGER (1..8) OPTIONAL, -- Need M
   sl-PriorityPreferredResourceSet-r17 [12] INTEGER (1..8) OPTIONAL, -- Need M
   sl-MaxSlotOffsetTRIV-r17 [13] INTEGER (1..8000) OPTIONAL, -- Need M
   sl-NumSubCH-PreferredResourceSet-r17 [14] INTEGER (1..27) OPTIONAL, -- Need M
   sl-ReservedPeriodPreferredResourceSet-r17 [15] INTEGER (1..16) OPTIONAL, -- Need M
   sl-DetermineResourceType-r17 [16] ENUMERATED { uea(0), ueb(1) } OPTIONAL,
   ...
}

SL-InterUE-CoordinationScheme2-r17 ::= SEQUENCE {
   sl-IUC-Scheme2-r17 [0] ENUMERATED { enabled(0) } OPTIONAL, -- Need R
   sl-RB-SetPSFCH-r17 [1] BIT STRING  (SIZE (10..275)) OPTIONAL, -- Need M
   sl-TypeUE-A-r17 [2] ENUMERATED { enabled(0) } OPTIONAL, -- Need R
   sl-PSFCH-Occasion-r17 [3] INTEGER (0..1) OPTIONAL, -- Need M
   sl-SlotLevelResourceExclusion-r17 [4] ENUMERATED { enabled(0) } OPTIONAL, -- Need R
   sl-OptionForCondition2-A-1-r17 [5] INTEGER (0..1) OPTIONAL, -- Need M
   sl-IndicationUE-B-r17 [6] ENUMERATED { enabled(0), disabled(1) } OPTIONAL,
   ...,
   [[
      sl-DeltaRSRP-Thresh-v1720 [7] INTEGER (-30..30) OPTIONAL
   ]]
}

-- TAG-SL-FREQCONFIGCOMMON-STOP
-- TAG-SL-INTERUE-COORDINATIONCONFIG-START
SL-InterUE-CoordinationConfig-r17 ::= SEQUENCE {
   sl-InterUE-CoordinationScheme1-r17 [0] SL-InterUE-CoordinationScheme1-r17
       OPTIONAL, -- Need M
   sl-InterUE-CoordinationScheme2-r17 [1] SL-InterUE-CoordinationScheme2-r17
       OPTIONAL,
   ...
}

-- TAG-SL-REPORTCONFIGLIST-STOP
-- TAG-SL-RESOURCEPOOL-START
SL-ResourcePool-r16 ::= SEQUENCE {
   sl-PSCCH-Config-r16 [0] EXPLICIT CHOICE {
      release [0] NULL,
      setup [1] EXPLICIT SL-PSCCH-Config-r16
   } OPTIONAL, -- Need M
   sl-PSSCH-Config-r16 [1] EXPLICIT CHOICE {
      release [0] NULL,
      setup [1] EXPLICIT SL-PSSCH-Config-r16
   } OPTIONAL, -- Need M
   sl-PSFCH-Config-r16 [2] EXPLICIT CHOICE {
      release [0] NULL,
      setup [1] EXPLICIT SL-PSFCH-Config-r16
   } OPTIONAL, -- Need M
   sl-SyncAllowed-r16 [3] SL-SyncAllowed-r16 OPTIONAL, -- Need M
   sl-SubchannelSize-r16 [4] ENUMERATED { n10(0), n12(1), n15(2), n20(3), 
      n25(4), n50(5), n75(6), n100(7) } OPTIONAL, -- Need M
   dummy [5] INTEGER (10..160) OPTIONAL, -- Need M
   sl-StartRB-Subchannel-r16 [6] INTEGER (0..265) OPTIONAL, -- Need M
   sl-NumSubchannel-r16 [7] INTEGER (1..27) OPTIONAL, -- Need M
   sl-Additional-MCS-Table-r16 [8] ENUMERATED { qam256(0), qam64LowSE(1), 
      qam256-qam64LowSE(2) } OPTIONAL, -- Need M
   sl-ThreshS-RSSI-CBR-r16 [9] INTEGER (0..45) OPTIONAL, -- Need M
   sl-TimeWindowSizeCBR-r16 [10] ENUMERATED { ms100(0), slot100(1) } OPTIONAL, -- Need M
   sl-TimeWindowSizeCR-r16 [11] ENUMERATED { ms1000(0), slot1000(1) } OPTIONAL,
       -- Need M
   sl-PTRS-Config-r16 [12] SL-PTRS-Config-r16 OPTIONAL, -- Need M
   sl-UE-SelectedConfigRP-r16 [13] SL-UE-SelectedConfigRP-r16 OPTIONAL, -- Need M
   sl-RxParametersNcell-r16 [14] SEQUENCE {
      sl-TDD-Configuration-r16 [0] TDD-UL-DL-ConfigCommon OPTIONAL, -- Need M
      sl-SyncConfigIndex-r16 [1] INTEGER (0..15)
   } OPTIONAL, -- Need M
   sl-ZoneConfigMCR-List-r16 [15] SEQUENCE (SIZE (16)) OF SL-ZoneConfigMCR-r16
       OPTIONAL, -- Need M
   sl-FilterCoefficient-r16 [16] FilterCoefficient OPTIONAL, -- Need M
   sl-RB-Number-r16 [17] INTEGER (10..275) OPTIONAL, -- Need M
   sl-PreemptionEnable-r16 [18] ENUMERATED { enabled(0), pl1(1), pl2(2), pl3(3)
      , pl4(4), pl5(5), pl6(6), pl7(7), pl8(8) } OPTIONAL, -- Need R
   sl-PriorityThreshold-UL-URLLC-r16 [19] INTEGER (1..9) OPTIONAL, -- Need M
   sl-PriorityThreshold-r16 [20] INTEGER (1..9) OPTIONAL, -- Need M
   sl-X-Overhead-r16 [21] ENUMERATED { n0(0), n3(1), n6(2), n9(3) } OPTIONAL, -- Need S
   sl-PowerControl-r16 [22] SL-PowerControl-r16 OPTIONAL, -- Need M
   sl-TxPercentageList-r16 [23] SL-TxPercentageList-r16 OPTIONAL, -- Need M
   sl-MinMaxMCS-List-r16 [24] SL-MinMaxMCS-List-r16 OPTIONAL,
   ...,
   [[
      sl-TimeResource-r16 [25] BIT STRING  (SIZE (10..160)) OPTIONAL
   ]],
   [[
      sl-PBPS-CPS-Config-r17 [26] EXPLICIT CHOICE {
         release [0] NULL,
         setup [1] EXPLICIT SL-PBPS-CPS-Config-r17
      } OPTIONAL,
      sl-InterUE-CoordinationConfig-r17 [27] EXPLICIT CHOICE {
         release [0] NULL,
         setup [1] EXPLICIT SL-InterUE-CoordinationConfig-r17
      } OPTIONAL
   ]]
}

SL-ResourcePoolConfig-r16 ::= SEQUENCE {
   sl-ResourcePoolID-r16 [0] SL-ResourcePoolID-r16,
   sl-ResourcePool-r16 [1] SL-ResourcePool-r16 OPTIONAL -- Need M
}

SL-TxPoolDedicated-r16 ::= SEQUENCE {
   sl-PoolToReleaseList-r16 [0] SEQUENCE (SIZE (1..maxNrofTXPool-r16)) OF SL-ResourcePoolID-r16
       OPTIONAL, -- Need N
   sl-PoolToAddModList-r16 [1] SEQUENCE (SIZE (1..maxNrofTXPool-r16)) OF 
      SL-ResourcePoolConfig-r16 OPTIONAL -- Need N
}

-- TAG-SL-BWP-DISCPOOLCONFIGCOMMON-STOP
-- TAG-SL-BWP-POOLCONFIG-START
SL-BWP-PoolConfig-r16 ::= SEQUENCE {
   sl-RxPool-r16 [0] SEQUENCE (SIZE (1..maxNrofRXPool-r16)) OF SL-ResourcePool-r16 OPTIONAL, -- Cond HO
   sl-TxPoolSelectedNormal-r16 [1] SL-TxPoolDedicated-r16 OPTIONAL, -- Need M
   sl-TxPoolScheduling-r16 [2] SL-TxPoolDedicated-r16 OPTIONAL, -- Need N
   sl-TxPoolExceptional-r16 [3] SL-ResourcePoolConfig-r16 OPTIONAL -- Need M
}

-- TAG-SL-BWP-CONFIGCOMMON-STOP
-- TAG-SL-BWP-DISCPOOLCONFIG-START
SL-BWP-DiscPoolConfig-r17 ::= SEQUENCE {
   sl-DiscRxPool-r17 [0] SEQUENCE (SIZE (1..maxNrofRXPool-r16)) OF SL-ResourcePool-r16 OPTIONAL, -- Cond HO
   sl-DiscTxPoolSelected-r17 [1] SL-TxPoolDedicated-r16 OPTIONAL, -- Need M
   sl-DiscTxPoolScheduling-r17 [2] SL-TxPoolDedicated-r16 OPTIONAL -- Need N
}

-- TAG-SL-BWP-CONFIG-START
SL-BWP-Config-r16 ::= SEQUENCE {
   sl-BWP-Id [0] BWP-Id,
   sl-BWP-Generic-r16 [1] SL-BWP-Generic-r16 OPTIONAL, -- Need M
   sl-BWP-PoolConfig-r16 [2] SL-BWP-PoolConfig-r16 OPTIONAL,
   ...,
   [[
      sl-BWP-PoolConfigPS-r17 [3] EXPLICIT CHOICE {
         release [0] NULL,
         setup [1] EXPLICIT SL-BWP-PoolConfig-r16
      } OPTIONAL,
      sl-BWP-DiscPoolConfig-r17 [4] EXPLICIT CHOICE {
         release [0] NULL,
         setup [1] EXPLICIT SL-BWP-DiscPoolConfig-r17
      } OPTIONAL
   ]]
}

SL-SSB-TimeAllocation-r16 ::= SEQUENCE {
   sl-NumSSB-WithinPeriod-r16 [0] ENUMERATED { n1(0), n2(1), n4(2), n8(3), 
      n16(4), n32(5), n64(6) } OPTIONAL, -- Need R
   sl-TimeOffsetSSB-r16 [1] INTEGER (0..1279) OPTIONAL, -- Need R
   sl-TimeInterval-r16 [2] INTEGER (0..639) OPTIONAL -- Need R
}

SL-SyncConfig-r16 ::= SEQUENCE {
   sl-SyncRefMinHyst-r16 [0] ENUMERATED { dB0(0), dB3(1), dB6(2), dB9(3), 
      dB12(4) } OPTIONAL, -- Need R
   sl-SyncRefDiffHyst-r16 [1] ENUMERATED { dB0(0), dB3(1), dB6(2), dB9(3), 
      dB12(4), dBinf(5) } OPTIONAL, -- Need R
   sl-FilterCoefficient-r16 [2] FilterCoefficient OPTIONAL, -- Need R
   sl-SSB-TimeAllocation1-r16 [3] SL-SSB-TimeAllocation-r16 OPTIONAL, -- Need R
   sl-SSB-TimeAllocation2-r16 [4] SL-SSB-TimeAllocation-r16 OPTIONAL, -- Need R
   sl-SSB-TimeAllocation3-r16 [5] SL-SSB-TimeAllocation-r16 OPTIONAL, -- Need R
   sl-SSID-r16 [6] INTEGER (0..671) OPTIONAL, -- Need R
   txParameters-r16 [7] SEQUENCE {
      syncTxThreshIC-r16 [0] SL-RSRP-Range-r16 OPTIONAL, -- Need R
      syncTxThreshOoC-r16 [1] SL-RSRP-Range-r16 OPTIONAL, -- Need R
      syncInfoReserved-r16 [2] BIT STRING  (SIZE (2)) OPTIONAL -- Need R
   },
   gnss-Sync-r16 [8] ENUMERATED { true(0) } OPTIONAL,
   ...
}

-- TAG-SL-SRAP-CONFIG-STOP
-- TAG-SL-SYNCCONFIG-START
SL-SyncConfigList-r16 ::= SEQUENCE (SIZE (1..maxSL-SyncConfig-r16)) OF SL-SyncConfig-r16

-- TAG-SL-DRX-CONFIGUCSEMISTATIC-STOP
-- TAG-SL-FREQCONFIG-START
SL-FreqConfig-r16 ::= SEQUENCE {
   sl-Freq-Id-r16 [0] SL-Freq-Id-r16,
   sl-SCS-SpecificCarrierList-r16 [1] SEQUENCE (SIZE (1..maxSCSs)) OF 
      SCS-SpecificCarrier,
   sl-AbsoluteFrequencyPointA-r16 [2] ARFCN-ValueNR OPTIONAL, -- Need M
   sl-AbsoluteFrequencySSB-r16 [3] ARFCN-ValueNR OPTIONAL, -- Need R
   frequencyShift7p5khzSL-r16 [4] ENUMERATED { true(0) } OPTIONAL, -- Cond V2X-SL-Shared
   valueN-r16 [5] INTEGER (-1..1),
   sl-BWP-ToReleaseList-r16 [6] SEQUENCE (SIZE (1..maxNrofSL-BWPs-r16)) OF BWP-Id OPTIONAL, -- Need N
   sl-BWP-ToAddModList-r16 [7] SEQUENCE (SIZE (1..maxNrofSL-BWPs-r16)) OF SL-BWP-Config-r16
       OPTIONAL, -- Need N
   sl-SyncConfigList-r16 [8] SL-SyncConfigList-r16 OPTIONAL, -- Need M
   sl-SyncPriority-r16 [9] ENUMERATED { gnss(0), gnbEnb(1) } OPTIONAL -- Need M
}

-- TAG-SL-RLC-CHANNELID-STOP
-- TAG-SL-RLC-CONFIG-START
SL-RLC-Config-r16 ::= CHOICE {
   sl-AM-RLC-r16 [0] SEQUENCE {
      sl-SN-FieldLengthAM-r16 [0] SN-FieldLengthAM OPTIONAL, -- Cond SLRBSetup
      sl-T-PollRetransmit-r16 [1] T-PollRetransmit,
      sl-PollPDU-r16 [2] PollPDU,
      sl-PollByte-r16 [3] PollByte,
      sl-MaxRetxThreshold-r16 [4] ENUMERATED { t1(0), t2(1), t3(2), t4(3), 
         t6(4), t8(5), t16(6), t32(7) },
      ...
   },
   sl-UM-RLC-r16 [1] SEQUENCE {
      sl-SN-FieldLengthUM-r16 [0] SN-FieldLengthUM OPTIONAL,
      ...
   },
   ...
}

-- TAG-SL-INTERUE-COORDINATIONCONFIG-STOP
-- TAG-SL-LOGICALCHANNELCONFIG-START
SL-LogicalChannelConfig-r16 ::= SEQUENCE {
   sl-Priority-r16 [0] INTEGER (1..8),
   sl-PrioritisedBitRate-r16 [1] ENUMERATED { kBps0(0), kBps8(1), kBps16(2), 
      kBps32(3), kBps64(4), kBps128(5), kBps256(6), kBps512(7), kBps1024(8), 
      kBps2048(9), kBps4096(10), kBps8192(11), kBps16384(12), kBps32768(13), 
      kBps65536(14), infinity(15) },
   sl-BucketSizeDuration-r16 [2] ENUMERATED { ms5(0), ms10(1), ms20(2), ms50(3)
      , ms100(4), ms150(5), ms300(6), ms500(7), ms1000(8), spare7(9), 
      spare6(10), spare5(11), spare4(12), spare3(13), spare2(14), spare1(15) },
   sl-ConfiguredGrantType1Allowed-r16 [3] ENUMERATED { true(0) } OPTIONAL, -- Need R
   sl-HARQ-FeedbackEnabled-r16 [4] ENUMERATED { enabled(0), disabled(1) }
       OPTIONAL, -- Need R
   sl-AllowedCG-List-r16 [5] SEQUENCE (SIZE (0..maxNrofCG-SL-1-r16)) OF SL-ConfigIndexCG-r16
       OPTIONAL,
                                                                                                                                     -- Need R
   sl-AllowedSCS-List-r16 [6] SEQUENCE (SIZE (1..maxSCSs)) OF SubcarrierSpacing
       OPTIONAL, -- Need R
   sl-MaxPUSCH-Duration-r16 [7] ENUMERATED { ms0p02(0), ms0p04(1), ms0p0625(2)
      , ms0p125(3), ms0p25(4), ms0p5(5), spare2(6), spare1(7) } OPTIONAL,
                                                                                                                                     -- Need R
   sl-LogicalChannelGroup-r16 [8] INTEGER (0..maxLCG-ID) OPTIONAL, -- Need R
   sl-SchedulingRequestId-r16 [9] SchedulingRequestId OPTIONAL, -- Need R
   sl-LogicalChannelSR-DelayTimerApplied-r16 [10] BOOLEAN OPTIONAL,
   ...
}

-- TAG-SL-RESOURCEPOOL-STOP
-- TAG-SL-RLC-BEARERCONFIG-START
SL-RLC-BearerConfig-r16 ::= SEQUENCE {
   sl-RLC-BearerConfigIndex-r16 [0] SL-RLC-BearerConfigIndex-r16,
   sl-ServedRadioBearer-r16 [1] SLRB-Uu-ConfigIndex-r16 OPTIONAL, -- Cond LCH-SetupOnly
   sl-RLC-Config-r16 [2] EXPLICIT SL-RLC-Config-r16 OPTIONAL, -- Cond LCH-Setup
   sl-MAC-LogicalChannelConfig-r16 [3] SL-LogicalChannelConfig-r16 OPTIONAL,
   ...
}

SL-PHY-MAC-RLC-Config-r16 ::= SEQUENCE {
   sl-ScheduledConfig-r16 [0] EXPLICIT CHOICE {
      release [0] NULL,
      setup [1] EXPLICIT SL-ScheduledConfig-r16
   } OPTIONAL, -- Need M
   sl-UE-SelectedConfig-r16 [1] EXPLICIT CHOICE {
      release [0] NULL,
      setup [1] EXPLICIT SL-UE-SelectedConfig-r16
   } OPTIONAL, -- Need M
   sl-FreqInfoToReleaseList-r16 [2] SEQUENCE (SIZE (1..maxNrofFreqSL-r16)) OF SL-Freq-Id-r16
       OPTIONAL, -- Need N
   sl-FreqInfoToAddModList-r16 [3] SEQUENCE (SIZE (1..maxNrofFreqSL-r16)) OF SL-FreqConfig-r16
       OPTIONAL, -- Need N
   sl-RLC-BearerToReleaseList-r16 [4] SEQUENCE (SIZE (1..maxSL-LCID-r16)) OF 
      SL-RLC-BearerConfigIndex-r16 OPTIONAL, -- Need N
   sl-RLC-BearerToAddModList-r16 [5] SEQUENCE (SIZE (1..maxSL-LCID-r16)) OF 
      SL-RLC-BearerConfig-r16 OPTIONAL, -- Need N
   sl-MaxNumConsecutiveDTX-r16 [6] ENUMERATED { n1(0), n2(1), n3(2), n4(3), 
      n6(4), n8(5), n16(6), n32(7) } OPTIONAL, -- Need M
   sl-CSI-Acquisition-r16 [7] ENUMERATED { enabled(0) } OPTIONAL, -- Need R
   sl-CSI-SchedulingRequestId-r16 [8] EXPLICIT CHOICE {
      release [0] NULL,
      setup [1] EXPLICIT SchedulingRequestId
   } OPTIONAL, -- Need M
   sl-SSB-PriorityNR-r16 [9] INTEGER (1..8) OPTIONAL, -- Need R
   networkControlledSyncTx-r16 [10] ENUMERATED { on(0), off(1) } OPTIONAL -- Need M
}

SL-PQI-r16 ::= CHOICE {
   sl-StandardizedPQI-r16 [0] INTEGER (0..255),
   sl-Non-StandardizedPQI-r16 [1] SEQUENCE {
      sl-ResourceType-r16 [0] ENUMERATED { gbr(0), non-GBR(1), 
         delayCriticalGBR(2), spare1(3) } OPTIONAL, -- Need R
      sl-PriorityLevel-r16 [1] INTEGER (1..8) OPTIONAL, -- Need R
      sl-PacketDelayBudget-r16 [2] INTEGER (0..1023) OPTIONAL, -- Need R
      sl-PacketErrorRate-r16 [3] INTEGER (0..9) OPTIONAL, -- Need R
      sl-AveragingWindow-r16 [4] INTEGER (0..4095) OPTIONAL, -- Need R
      sl-MaxDataBurstVolume-r16 [5] INTEGER (0..4095) OPTIONAL,
      ...
   }
}

-- TAG-SL-QOS-FLOWIDENTITY-STOP
-- TAG-SL-QOS-PROFILE-START
SL-QoS-Profile-r16 ::= SEQUENCE {
   sl-PQI-r16 [0] EXPLICIT SL-PQI-r16 OPTIONAL, -- Need R
   sl-GFBR-r16 [1] INTEGER (0..4000000000) OPTIONAL, -- Need R
   sl-MFBR-r16 [2] INTEGER (0..4000000000) OPTIONAL, -- Need R
   sl-Range-r16 [3] INTEGER (1..1000) OPTIONAL,
   ...
}

SL-MappedQoS-FlowsListDedicated-r16 ::= SEQUENCE {
   sl-MappedQoS-FlowsToAddList-r16 [0] SEQUENCE (SIZE (1..maxNrofSL-QFIs-r16)) OF 
      SL-QoS-FlowIdentity-r16 OPTIONAL, -- Need N
   sl-MappedQoS-FlowsToReleaseList-r16 [1] SEQUENCE (SIZE (1..maxNrofSL-QFIs-r16)) OF 
      SL-QoS-FlowIdentity-r16 OPTIONAL -- Need N
}

-- TAG-SL-SCHEDULEDCONFIG-STOP
-- TAG-SL-SDAP-CONFIG-START
SL-SDAP-Config-r16 ::= SEQUENCE {
   sl-SDAP-Header-r16 [0] ENUMERATED { present(0), absent(1) },
   sl-DefaultRB-r16 [1] BOOLEAN,
   sl-MappedQoS-Flows-r16 [2] EXPLICIT CHOICE {
      sl-MappedQoS-FlowsList-r16 [0] SEQUENCE (SIZE (1..maxNrofSL-QFIs-r16)) OF SL-QoS-Profile-r16
         ,
      sl-MappedQoS-FlowsListDedicated-r16 [1] 
         SL-MappedQoS-FlowsListDedicated-r16
   } OPTIONAL, -- Need M
   sl-CastType-r16 [3] ENUMERATED { broadcast(0), groupcast(1), unicast(2), 
      spare1(3) } OPTIONAL,
   ...
}

-- TAG-SL-PBPS-CPS-CONFIG-STOP
-- TAG-SL-PDCP-CONFIG-START
SL-PDCP-Config-r16 ::= SEQUENCE {
   sl-DiscardTimer-r16 [0] ENUMERATED { ms3(0), ms10(1), ms20(2), ms25(3), 
      ms30(4), ms40(5), ms50(6), ms60(7), ms75(8), ms100(9), ms150(10), 
      ms200(11), ms250(12), ms300(13), ms500(14), ms750(15), ms1500(16), 
      infinity(17) } OPTIONAL, -- Cond Setup
   sl-PDCP-SN-Size-r16 [1] ENUMERATED { len12bits(0), len18bits(1) } OPTIONAL, -- Cond Setup2
   sl-OutOfOrderDelivery [2] ENUMERATED { true(0) } OPTIONAL,
   ...
}

-- TAG-SL-QuantityConfig-STOP
-- TAG-SL-RADIOBEARERCONFIG-START
SL-RadioBearerConfig-r16 ::= SEQUENCE {
   slrb-Uu-ConfigIndex-r16 [0] SLRB-Uu-ConfigIndex-r16,
   sl-SDAP-Config-r16 [1] SL-SDAP-Config-r16 OPTIONAL, -- Cond SLRBSetup
   sl-PDCP-Config-r16 [2] SL-PDCP-Config-r16 OPTIONAL, -- Cond SLRBSetup
   sl-TransRange-r16 [3] ENUMERATED { m20(0), m50(1), m80(2), m100(3), m120(4)
      , m150(5), m180(6), m200(7), m220(8), m250(9), m270(10), m300(11), 
      m350(12), m370(13), m400(14), m420(15), m450(16), m480(17), m500(18), 
      m550(19), m600(20), m700(21), m1000(22), spare9(23), spare8(24), 
      spare7(25), spare6(26), spare5(27), spare4(28), spare3(29), spare2(30), 
      spare1(31) } OPTIONAL,
   ...
}

SL-MeasObjectToRemoveList-r16 ::= SEQUENCE (SIZE (1..maxNrofSL-ObjectId-r16)) OF SL-MeasObjectId-r16

SL-MeasObject-r16 ::= SEQUENCE {
   frequencyInfoSL-r16 [0] ARFCN-ValueNR,
   ...
}

SL-MeasObjectInfo-r16 ::= SEQUENCE {
   sl-MeasObjectId-r16 [0] SL-MeasObjectId-r16,
   sl-MeasObject-r16 [1] SL-MeasObject-r16,
   ...
}

-- TAG-SL-MEASIDLIST-STOP
-- TAG-SL-MEASOBJECTLIST-START
SL-MeasObjectList-r16 ::= SEQUENCE (SIZE (1..maxNrofSL-ObjectId-r16)) OF SL-MeasObjectInfo-r16

SL-ReportConfigToRemoveList-r16 ::= SEQUENCE (SIZE (1..maxNrofSL-ReportConfigId-r16)) OF 
   SL-ReportConfigId-r16

SL-MeasReportQuantity-r16 ::= CHOICE {
   sl-RSRP-r16 [0] BOOLEAN,
   ...
}

SL-PeriodicalReportConfig-r16 ::= SEQUENCE {
   sl-ReportInterval-r16 [0] ReportInterval,
   sl-ReportAmount-r16 [1] ENUMERATED { r1(0), r2(1), r4(2), r8(3), r16(4), 
      r32(5), r64(6), infinity(7) },
   sl-ReportQuantity-r16 [2] EXPLICIT SL-MeasReportQuantity-r16,
   sl-RS-Type-r16 [3] SL-RS-Type-r16,
   ...
}

SL-MeasTriggerQuantity-r16 ::= CHOICE {
   sl-RSRP-r16 [0] RSRP-Range,
   ...
}

SL-EventTriggerConfig-r16 ::= SEQUENCE {
   sl-EventId-r16 [0] EXPLICIT CHOICE {
      eventS1-r16 [0] SEQUENCE {
         s1-Threshold-r16 [0] EXPLICIT SL-MeasTriggerQuantity-r16,
         sl-ReportOnLeave-r16 [1] BOOLEAN,
         sl-Hysteresis-r16 [2] Hysteresis,
         sl-TimeToTrigger-r16 [3] TimeToTrigger,
         ...
      },
      eventS2-r16 [1] SEQUENCE {
         s2-Threshold-r16 [0] EXPLICIT SL-MeasTriggerQuantity-r16,
         sl-ReportOnLeave-r16 [1] BOOLEAN,
         sl-Hysteresis-r16 [2] Hysteresis,
         sl-TimeToTrigger-r16 [3] TimeToTrigger,
         ...
      },
      ...
   },
   sl-ReportInterval-r16 [1] ReportInterval,
   sl-ReportAmount-r16 [2] ENUMERATED { r1(0), r2(1), r4(2), r8(3), r16(4), 
      r32(5), r64(6), infinity(7) },
   sl-ReportQuantity-r16 [3] EXPLICIT SL-MeasReportQuantity-r16,
   sl-RS-Type-r16 [4] SL-RS-Type-r16,
   ...
}

SL-ReportConfig-r16 ::= SEQUENCE {
   sl-ReportType-r16 [0] EXPLICIT CHOICE {
      sl-Periodical-r16 [0] SL-PeriodicalReportConfig-r16,
      sl-EventTriggered-r16 [1] SL-EventTriggerConfig-r16,
      ...
   },
   ...
}

SL-ReportConfigInfo-r16 ::= SEQUENCE {
   sl-ReportConfigId-r16 [0] SL-ReportConfigId-r16,
   sl-ReportConfig-r16 [1] SL-ReportConfig-r16,
   ...
}

-- TAG-SL-REMOTEUE-CONFIG-STOP
-- TAG-SL-REPORTCONFIGLIST-START
SL-ReportConfigList-r16 ::= SEQUENCE (SIZE (1..maxNrofSL-ReportConfigId-r16)) OF SL-ReportConfigInfo-r16

SL-MeasIdToRemoveList-r16 ::= SEQUENCE (SIZE (1..maxNrofSL-MeasId-r16)) OF SL-MeasId-r16

SL-MeasIdInfo-r16 ::= SEQUENCE {
   sl-MeasId-r16 [0] SL-MeasId-r16,
   sl-MeasObjectId-r16 [1] SL-MeasObjectId-r16,
   sl-ReportConfigId-r16 [2] SL-ReportConfigId-r16,
   ...
}

-- TAG-SL-MEASCONFIGINFO-STOP
-- TAG-SL-MEASIDLIST-START
SL-MeasIdList-r16 ::= SEQUENCE (SIZE (1..maxNrofSL-MeasId-r16)) OF SL-MeasIdInfo-r16

-- TAG-SL-QOS-PROFILE-STOP
-- TAG-SL-QUANTITYCONFIG-START
SL-QuantityConfig-r16 ::= SEQUENCE {
   sl-FilterCoefficientDMRS-r16 [0] FilterCoefficient DEFAULT fc4,
   ...
}

SL-MeasConfig-r16 ::= SEQUENCE {
   sl-MeasObjectToRemoveList-r16 [0] SL-MeasObjectToRemoveList-r16 OPTIONAL, -- Need N
   sl-MeasObjectToAddModList-r16 [1] SL-MeasObjectList-r16 OPTIONAL, -- Need N
   sl-ReportConfigToRemoveList-r16 [2] SL-ReportConfigToRemoveList-r16 OPTIONAL
      , -- Need N
   sl-ReportConfigToAddModList-r16 [3] SL-ReportConfigList-r16 OPTIONAL, -- Need N
   sl-MeasIdToRemoveList-r16 [4] SL-MeasIdToRemoveList-r16 OPTIONAL, -- Need N
   sl-MeasIdToAddModList-r16 [5] SL-MeasIdList-r16 OPTIONAL, -- Need N
   sl-QuantityConfig-r16 [6] SL-QuantityConfig-r16 OPTIONAL,
   ...
}

-- TAG-SL-MEASCONFIGCOMMON-STOP
-- TAG-SL-MEASCONFIGINFO-START
SL-MeasConfigInfo-r16 ::= SEQUENCE {
   sl-DestinationIndex-r16 [0] SL-DestinationIndex-r16,
   sl-MeasConfig-r16 [1] SL-MeasConfig-r16,
   ...
}

SL-DRX-GC-BC-QoS-r17 ::= SEQUENCE {
   sl-DRX-GC-BC-MappedQoS-FlowList-r17 [0] SEQUENCE (SIZE (1..maxNrofSL-QFIs-r16)) OF 
      SL-QoS-Profile-r16 OPTIONAL, -- Need M
   sl-DRX-GC-BC-OnDurationTimer-r17 [1] EXPLICIT CHOICE {
      subMilliSeconds [0] INTEGER (1..31),
      milliSeconds [1] ENUMERATED { ms1(0), ms2(1), ms3(2), ms4(3), ms5(4), 
         ms6(5), ms8(6), ms10(7), ms20(8), ms30(9), ms40(10), ms50(11), 
         ms60(12), ms80(13), ms100(14), ms200(15), ms300(16), ms400(17), 
         ms500(18), ms600(19), ms800(20), ms1000(21), ms1200(22), ms1600(23), 
         spare8(24), spare7(25), spare6(26), spare5(27), spare4(28), spare3(29)
         , spare2(30), spare1(31) }
   },
   sl-DRX-GC-InactivityTimer-r17 [2] ENUMERATED { ms0(0), ms1(1), ms2(2), 
      ms3(3), ms4(4), ms5(5), ms6(6), ms8(7), ms10(8), ms20(9), ms30(10), 
      ms40(11), ms50(12), ms60(13), ms80(14), ms100(15), ms200(16), ms300(17), 
      ms500(18), ms750(19), ms1280(20), ms1920(21), ms2560(22), spare9(23), 
      spare8(24), spare7(25), spare6(26), spare5(27), spare4(28), spare3(29), 
      spare2(30), spare1(31) },
   sl-DRX-GC-BC-Cycle-r17 [3] ENUMERATED { ms10(0), ms20(1), ms32(2), ms40(3), 
      ms60(4), ms64(5), ms70(6), ms80(7), ms128(8), ms160(9), ms256(10), 
      ms320(11), ms512(12), ms640(13), ms1024(14), ms1280(15), ms2048(16), 
      ms2560(17), ms5120(18), ms10240(19), spare12(20), spare11(21), 
      spare10(22), spare9(23), spare8(24), spare7(25), spare6(26), spare5(27), 
      spare4(28), spare3(29), spare2(30), spare1(31) },
   ...
}

SL-DRX-GC-Generic-r17 ::= SEQUENCE {
   sl-DRX-GC-HARQ-RTT-Timer1-r17 [0] ENUMERATED { sl0(0), sl1(1), sl2(2), 
      sl4(3), spare4(4), spare3(5), spare2(6), spare1(7) } OPTIONAL, -- Need M
   sl-DRX-GC-HARQ-RTT-Timer2-r17 [1] ENUMERATED { sl0(0), sl1(1), sl2(2), 
      sl4(3), spare4(4), spare3(5), spare2(6), spare1(7) } OPTIONAL, -- Need M
   sl-DRX-GC-RetransmissionTimer-r17 [2] ENUMERATED { sl0(0), sl1(1), sl2(2), 
      sl4(3), sl6(4), sl8(5), sl16(6), sl24(7), sl33(8), sl40(9), sl64(10), 
      sl80(11), sl96(12), sl112(13), sl128(14), sl160(15), sl320(16), 
      spare15(17), spare14(18), spare13(19), spare12(20), spare11(21), 
      spare10(22), spare9(23), spare8(24), spare7(25), spare6(26), spare5(27), 
      spare4(28), spare3(29), spare2(30), spare1(31) }
}

-- TAG-SL-DRX-CONFIG-STOP
-- TAG-SL-DRX-CONFIGGC-BC-START
SL-DRX-ConfigGC-BC-r17 ::= SEQUENCE {
   sl-DRX-GC-BC-PerQoS-List-r17 [0] SEQUENCE (SIZE (1..maxSL-GC-BC-DRX-QoS-r17)) OF 
      SL-DRX-GC-BC-QoS-r17 OPTIONAL, -- Need M
   sl-DRX-GC-generic-r17 [1] SL-DRX-GC-Generic-r17 OPTIONAL, -- Need M
   sl-DefaultDRX-GC-BC-r17 [2] SL-DRX-GC-BC-QoS-r17 OPTIONAL,
   ...
}

-- TAG-SL-DRX-CONFIGGC-BC-STOP
-- TAG-DRX-CONFIGUC-START
SL-DRX-ConfigUC-r17 ::= SEQUENCE {
   sl-drx-onDurationTimer-r17 [0] EXPLICIT CHOICE {
      subMilliSeconds [0] INTEGER (1..31),
      milliSeconds [1] ENUMERATED { ms1(0), ms2(1), ms3(2), ms4(3), ms5(4), 
         ms6(5), ms8(6), ms10(7), ms20(8), ms30(9), ms40(10), ms50(11), 
         ms60(12), ms80(13), ms100(14), ms200(15), ms300(16), ms400(17), 
         ms500(18), ms600(19), ms800(20), ms1000(21), ms1200(22), ms1600(23), 
         spare8(24), spare7(25), spare6(26), spare5(27), spare4(28), spare3(29)
         , spare2(30), spare1(31) }
   },
   sl-drx-InactivityTimer-r17 [1] ENUMERATED { ms0(0), ms1(1), ms2(2), ms3(3), 
      ms4(4), ms5(5), ms6(6), ms8(7), ms10(8), ms20(9), ms30(10), ms40(11), 
      ms50(12), ms60(13), ms80(14), ms100(15), ms200(16), ms300(17), ms500(18)
      , ms750(19), ms1280(20), ms1920(21), ms2560(22), spare9(23), spare8(24), 
      spare7(25), spare6(26), spare5(27), spare4(28), spare3(29), spare2(30), 
      spare1(31) },
   sl-drx-HARQ-RTT-Timer1-r17 [2] ENUMERATED { sl0(0), sl1(1), sl2(2), sl4(3), 
      spare4(4), spare3(5), spare2(6), spare1(7) } OPTIONAL, -- Need M
   sl-drx-HARQ-RTT-Timer2-r17 [3] ENUMERATED { sl0(0), sl1(1), sl2(2), sl4(3), 
      spare4(4), spare3(5), spare2(6), spare1(7) } OPTIONAL, -- Need M
   sl-drx-RetransmissionTimer-r17 [4] ENUMERATED { sl0(0), sl1(1), sl2(2), 
      sl4(3), sl6(4), sl8(5), sl16(6), sl24(7), sl33(8), sl40(9), sl64(10), 
      sl80(11), sl96(12), sl112(13), sl128(14), sl160(15), sl320(16), 
      spare15(17), spare14(18), spare13(19), spare12(20), spare11(21), 
      spare10(22), spare9(23), spare8(24), spare7(25), spare6(26), spare5(27), 
      spare4(28), spare3(29), spare2(30), spare1(31) },
   sl-drx-CycleStartOffset-r17 [5] EXPLICIT CHOICE {
      ms10 [0] INTEGER (0..9),
      ms20 [1] INTEGER (0..19),
      ms32 [2] INTEGER (0..31),
      ms40 [3] INTEGER (0..39),
      ms60 [4] INTEGER (0..59),
      ms64 [5] INTEGER (0..63),
      ms70 [6] INTEGER (0..69),
      ms80 [7] INTEGER (0..79),
      ms128 [8] INTEGER (0..127),
      ms160 [9] INTEGER (0..159),
      ms256 [10] INTEGER (0..255),
      ms320 [11] INTEGER (0..319),
      ms512 [12] INTEGER (0..511),
      ms640 [13] INTEGER (0..639),
      ms1024 [14] INTEGER (0..1023),
      ms1280 [15] INTEGER (0..1279),
      ms2048 [16] INTEGER (0..2047),
      ms2560 [17] INTEGER (0..2559),
      ms5120 [18] INTEGER (0..5119),
      ms10240 [19] INTEGER (0..10239)
   },
   sl-drx-SlotOffset [6] INTEGER (0..31)
}

SL-DRX-ConfigUC-Info-r17 ::= SEQUENCE {
   sl-DestinationIndex-r17 [0] SL-DestinationIndex-r16 OPTIONAL, -- Need N
   sl-DRX-ConfigUC-r17 [1] SL-DRX-ConfigUC-r17 OPTIONAL,
   ...
}

-- TAG-SL-DESTINATIONIDENTITY-STOP
-- TAG-SL-DRX-CONFIG-START
SL-DRX-Config-r17 ::= SEQUENCE {
   sl-DRX-ConfigGC-BC-r17 [0] SL-DRX-ConfigGC-BC-r17 OPTIONAL, -- Cond HO
   sl-DRX-ConfigUC-ToReleaseList-r17 [1] SEQUENCE (SIZE (1..maxNrofSL-Dest-r16)) OF 
      SL-DestinationIndex-r16 OPTIONAL, -- Need N
   sl-DRX-ConfigUC-ToAddModList-r17 [2] SEQUENCE (SIZE (1..maxNrofSL-Dest-r16)) OF 
      SL-DRX-ConfigUC-Info-r17 OPTIONAL,
   ...
}

-- TAG-RLC-BEARERCONFIGINDEX-STOP
-- TAG-SL-RLC-RLC-CHANNEL-CONFIG-START
SL-RLC-ChannelConfig-r17 ::= SEQUENCE {
   sl-RLC-ChannelID-r17 [0] SL-RLC-ChannelID-r17,
   sl-RLC-Config-r17 [1] EXPLICIT SL-RLC-Config-r16 OPTIONAL, -- Need M
   sl-MAC-LogicalChannelConfig-r17 [2] SL-LogicalChannelConfig-r16 OPTIONAL, -- Need M
   sl-PacketDelayBudget-r17 [3] INTEGER (0..1023) OPTIONAL,
   ...
}

SL-PHY-MAC-RLC-Config-v1700 ::= SEQUENCE {
   sl-DRX-Config-r17 [0] SL-DRX-Config-r17 OPTIONAL, -- Need M
   sl-RLC-ChannelToReleaseList-r17 [1] SEQUENCE (SIZE (1..maxSL-LCID-r16)) OF 
      SL-RLC-ChannelID-r17 OPTIONAL, -- Cond L2U2N
   sl-RLC-ChannelToAddModList-r17 [2] SEQUENCE (SIZE (1..maxSL-LCID-r16)) OF 
      SL-RLC-ChannelConfig-r17 OPTIONAL,
   ...
}

-- TAG-SL-RADIOBEARERCONFIG-STOP
-- TAG-SL-RELAYUE-CONFIG-START
SL-RelayUE-Config-r17 ::= SEQUENCE {
   threshHighRelay-r17 [0] RSRP-Range OPTIONAL, -- Need R
   threshLowRelay-r17 [1] RSRP-Range OPTIONAL, -- Need R
   hystMaxRelay-r17 [2] Hysteresis OPTIONAL, -- Cond ThreshHighRelay
   hystMinRelay-r17 [3] Hysteresis OPTIONAL -- Cond ThreshLowRelay
}

SL-ReselectionConfig-r17 ::= SEQUENCE {
   sl-RSRP-Thresh-r17 [0] SL-RSRP-Range-r16 OPTIONAL, -- Need R
   sl-FilterCoefficientRSRP-r17 [1] FilterCoefficient OPTIONAL, -- Need R
   sl-HystMin-r17 [2] Hysteresis OPTIONAL -- Cond SL-RSRP-Thresh
}

-- TAG-SL-RELAYUE-CONFIG-STOP
-- TAG-SL-REMOTEUE-CONFIG-START
SL-RemoteUE-Config-r17 ::= SEQUENCE {
   threshHighRemote-r17 [0] RSRP-Range OPTIONAL, -- Need R
   hystMaxRemote-r17 [1] Hysteresis OPTIONAL, -- Cond ThreshHighRemote
   sl-ReselectionConfig-r17 [2] SL-ReselectionConfig-r17 OPTIONAL -- Need R
}

SL-DiscConfig-r17 ::= SEQUENCE {
   sl-RelayUE-Config-r17 [0] EXPLICIT CHOICE {
      release [0] NULL,
      setup [1] EXPLICIT SL-RelayUE-Config-r17
   } OPTIONAL, -- Cond L2RelayUE
   sl-RemoteUE-Config-r17 [1] EXPLICIT CHOICE {
      release [0] NULL,
      setup [1] EXPLICIT SL-RemoteUE-Config-r17
   } OPTIONAL -- Cond L2RemoteUE
}

-- TAG-SL-CBR-COMMONTXCONFIGLIST-STOP
-- TAG-SL-CONFIGDEDICATEDNR-START
SL-ConfigDedicatedNR-r16 ::= SEQUENCE {
   sl-PHY-MAC-RLC-Config-r16 [0] SL-PHY-MAC-RLC-Config-r16 OPTIONAL, -- Need M
   sl-RadioBearerToReleaseList-r16 [1] SEQUENCE (SIZE (1..maxNrofSLRB-r16)) OF 
      SLRB-Uu-ConfigIndex-r16 OPTIONAL, -- Need N
   sl-RadioBearerToAddModList-r16 [2] SEQUENCE (SIZE (1..maxNrofSLRB-r16)) OF 
      SL-RadioBearerConfig-r16 OPTIONAL, -- Need N
   sl-MeasConfigInfoToReleaseList-r16 [3] SEQUENCE (SIZE (1..maxNrofSL-Dest-r16)) OF 
      SL-DestinationIndex-r16 OPTIONAL, -- Need N
   sl-MeasConfigInfoToAddModList-r16 [4] SEQUENCE (SIZE (1..maxNrofSL-Dest-r16)) OF 
      SL-MeasConfigInfo-r16 OPTIONAL, -- Need N
   t400-r16 [5] ENUMERATED { ms100(0), ms200(1), ms300(2), ms400(3), ms600(4), 
      ms1000(5), ms1500(6), ms2000(7) } OPTIONAL,
   ...,
   [[
      sl-PHY-MAC-RLC-Config-v1700 [6] EXPLICIT CHOICE {
         release [0] NULL,
         setup [1] EXPLICIT SL-PHY-MAC-RLC-Config-v1700
      } OPTIONAL,
      sl-DiscConfig-r17 [7] EXPLICIT CHOICE {
         release [0] NULL,
         setup [1] EXPLICIT SL-DiscConfig-r17
      } OPTIONAL
   ]]
}

SL-RemoteUE-RB-Identity-r17 ::= CHOICE {
   srb-Identity-r17 [0] INTEGER (0..3),
   drb-Identity-r17 [1] DRB-Identity,
   ...
}

SL-MappingToAddMod-r17 ::= SEQUENCE {
   sl-RemoteUE-RB-Identity-r17 [0] EXPLICIT SL-RemoteUE-RB-Identity-r17,
   sl-EgressRLC-ChannelUu-r17 [1] Uu-RelayRLC-ChannelID-r17 OPTIONAL, -- Cond L2RelayUE
   sl-EgressRLC-ChannelPC5-r17 [2] SL-RLC-ChannelID-r17 OPTIONAL,
   ...
}

-- TAG-SL-SOURCEIDENTITY-STOP
-- TAG-SL-SRAP-CONFIG-START
SL-SRAP-Config-r17 ::= SEQUENCE {
   sl-LocalIdentity-r17 [0] INTEGER (0..255) OPTIONAL, -- Need M
   sl-MappingToAddModList-r17 [1] SEQUENCE (SIZE (1..maxLC-ID)) OF 
      SL-MappingToAddMod-r17 OPTIONAL, -- Need N
   sl-MappingToReleaseList-r17 [2] SEQUENCE (SIZE (1..maxLC-ID)) OF 
      SL-RemoteUE-RB-Identity-r17 OPTIONAL,
   ...
}

-- TAG-SL-L2RELAYUE-CONFIG-STOP
-- TAG-SL-L2REMOTEUE-CONFIG-START
SL-L2RemoteUE-Config-r17 ::= SEQUENCE {
   sl-SRAP-ConfigRemote-r17 [0] SL-SRAP-Config-r17 OPTIONAL, --Need M
   sl-UEIdentityRemote-r17 [1] RNTI-Value OPTIONAL,
   ...
}

RRCSetup-v1700-IEs ::= SEQUENCE {
   sl-ConfigDedicatedNR-r17 [0] SL-ConfigDedicatedNR-r16 OPTIONAL, -- Cond L2RemoteUE
   sl-L2RemoteUE-Config-r17 [1] SL-L2RemoteUE-Config-r17 OPTIONAL, -- Cond L2RemoteUE
   nonCriticalExtension [2] SEQUENCE {

   } OPTIONAL
}

RRCSetup-IEs ::= SEQUENCE {
   radioBearerConfig [0] RadioBearerConfig,
   masterCellGroup [1] OCTET STRING (CONTAINING CellGroupConfig),
   lateNonCriticalExtension [2] OCTET STRING OPTIONAL,
   nonCriticalExtension [3] RRCSetup-v1700-IEs OPTIONAL
}

-- TAG-RRCRESUMEREQUEST1-STOP
-- TAG-RRCSETUP-START
RRCSetup ::= SEQUENCE {
   rrc-TransactionIdentifier [0] RRC-TransactionIdentifier,
   criticalExtensions [1] EXPLICIT CHOICE {
      rrcSetup [0] RRCSetup-IEs,
      criticalExtensionsFuture [1] SEQUENCE {

      }
   }
}

DL-CCCH-MessageType ::= CHOICE {
   c1 [0] EXPLICIT CHOICE {
      rrcReject [0] RRCReject,
      rrcSetup [1] RRCSetup,
      spare2 [2] NULL,
      spare1 [3] NULL
   },
   messageClassExtension [1] SEQUENCE {

   }
}

-- TAG-BCCH-DL-SCH-MESSAGE-STOP
-- TAG-DL-CCCH-MESSAGE-START
DL-CCCH-Message ::= SEQUENCE {
   message [0] EXPLICIT DL-CCCH-MessageType
}

MeasObjectToRemoveList ::= SEQUENCE (SIZE (1..maxNrofObjectId)) OF MeasObjectId

SSB-MTC2 ::= SEQUENCE {
   pci-List [0] SEQUENCE (SIZE (1..maxNrofPCIsPerSMTC)) OF PhysCellId OPTIONAL, -- Need M
   periodicity [1] ENUMERATED { sf5(0), sf10(1), sf20(2), sf40(3), sf80(4), 
      spare3(5), spare2(6), spare1(7) }
}

SSB-PositionQCL-CellsToAddMod-r16 ::= SEQUENCE {
   physCellId-r16 [0] PhysCellId,
   ssb-PositionQCL-r16 [1] SSB-PositionQCL-Relation-r16
}

SSB-PositionQCL-CellsToAddModList-r16 ::= SEQUENCE (SIZE (1..maxNrofCellMeas)) OF 
   SSB-PositionQCL-CellsToAddMod-r16

-- TAG-PCIARFCNNR-STOP
-- TAG-PCI-LIST-START
PCI-List ::= SEQUENCE (SIZE (1..maxNrofCellMeas)) OF PhysCellId

SSB-PositionQCL-Cell-r17 ::= SEQUENCE {
   physCellId-r17 [0] PhysCellId,
   ssb-PositionQCL-r17 [1] SSB-PositionQCL-Relation-r17
}

SSB-PositionQCL-CellList-r17 ::= SEQUENCE (SIZE (1..maxNrofCellMeas)) OF 
   SSB-PositionQCL-Cell-r17

SSB-ConfigMobility ::= SEQUENCE {
   ssb-ToMeasure [0] EXPLICIT CHOICE {
      release [0] NULL,
      setup [1] EXPLICIT SSB-ToMeasure
   } OPTIONAL, -- Need M
   deriveSSB-IndexFromCell [1] BOOLEAN,
   ss-RSSI-Measurement [2] SS-RSSI-Measurement OPTIONAL,
   ...,
   [[
      ssb-PositionQCL-Common-r16 [3] SSB-PositionQCL-Relation-r16 OPTIONAL,
      ssb-PositionQCL-CellsToAddModList-r16 [4] 
         SSB-PositionQCL-CellsToAddModList-r16 OPTIONAL,
      ssb-PositionQCL-CellsToRemoveList-r16 [5] PCI-List OPTIONAL
   ]],
   [[
      deriveSSB-IndexFromCellInter-r17 [6] ServCellIndex OPTIONAL,
      ssb-PositionQCL-Common-r17 [7] SSB-PositionQCL-Relation-r17 OPTIONAL,
      ssb-PositionQCL-Cells-r17 [8] EXPLICIT CHOICE {
         release [0] NULL,
         setup [1] EXPLICIT SSB-PositionQCL-CellList-r17
      } OPTIONAL
   ]],
   [[
      cca-CellsToAddModList-r17 [9] PCI-List OPTIONAL,
      cca-CellsToRemoveList-r17 [10] PCI-List OPTIONAL
   ]]
}

CSI-RS-Resource-Mobility ::= SEQUENCE {
   csi-RS-Index [0] CSI-RS-Index,
   slotConfig [1] EXPLICIT CHOICE {
      ms4 [0] INTEGER (0..31),
      ms5 [1] INTEGER (0..39),
      ms10 [2] INTEGER (0..79),
      ms20 [3] INTEGER (0..159),
      ms40 [4] INTEGER (0..319)
   },
   associatedSSB [2] SEQUENCE {
      ssb-Index [0] SSB-Index,
      isQuasiColocated [1] BOOLEAN
   } OPTIONAL, -- Need R
   frequencyDomainAllocation [3] EXPLICIT CHOICE {
      row1 [0] BIT STRING  (SIZE (4)),
      row2 [1] BIT STRING  (SIZE (12))
   },
   firstOFDMSymbolInTimeDomain [4] INTEGER (0..13),
   sequenceGenerationConfig [5] INTEGER (0..1023),
   ...,
   [[
      slotConfig-r17 [6] EXPLICIT CHOICE {
         ms4 [0] INTEGER (0..255),
         ms5 [1] INTEGER (0..319),
         ms10 [2] INTEGER (0..639),
         ms20 [3] INTEGER (0..1279),
         ms40 [4] INTEGER (0..2559)
      } OPTIONAL
   ]]
}

CSI-RS-CellMobility ::= SEQUENCE {
   cellId [0] PhysCellId,
   csi-rs-MeasurementBW [1] SEQUENCE {
      nrofPRBs [0] ENUMERATED { size24(0), size48(1), size96(2), size192(3), 
         size264(4) },
      startPRB [1] INTEGER (0..2169)
   },
   density [2] ENUMERATED { d1(0), d3(1) } OPTIONAL, -- Need R
   csi-rs-ResourceList-Mobility [3] SEQUENCE (SIZE (1..maxNrofCSI-RS-ResourcesRRM)) OF 
      CSI-RS-Resource-Mobility
}

-- TAG-CSI-RESOURCEPERIODICITYANDOFFSET-STOP
-- TAG-CSI-RS-RESOURCECONFIGMOBILITY-START
CSI-RS-ResourceConfigMobility ::= SEQUENCE {
   subcarrierSpacing [0] SubcarrierSpacing,
   csi-RS-CellList-Mobility [1] SEQUENCE (SIZE (1..maxNrofCSI-RS-CellsRRM)) OF CSI-RS-CellMobility,
   ...,
   [[
      refServCellIndex [2] ServCellIndex OPTIONAL
   ]]
}

ReferenceSignalConfig ::= SEQUENCE {
   ssb-ConfigMobility [0] SSB-ConfigMobility OPTIONAL, -- Need M
   csi-rs-ResourceConfigMobility [1] EXPLICIT CHOICE {
      release [0] NULL,
      setup [1] EXPLICIT CSI-RS-ResourceConfigMobility
   } OPTIONAL -- Need M
}

Q-OffsetRangeList ::= SEQUENCE {
   rsrpOffsetSSB [0] Q-OffsetRange DEFAULT dB0,
   rsrqOffsetSSB [1] Q-OffsetRange DEFAULT dB0,
   sinrOffsetSSB [2] Q-OffsetRange DEFAULT dB0,
   rsrpOffsetCSI-RS [3] Q-OffsetRange DEFAULT dB0,
   rsrqOffsetCSI-RS [4] Q-OffsetRange DEFAULT dB0,
   sinrOffsetCSI-RS [5] Q-OffsetRange DEFAULT dB0
}

CellsToAddMod ::= SEQUENCE {
   physCellId [0] PhysCellId,
   cellIndividualOffset [1] Q-OffsetRangeList
}

CellsToAddModList ::= SEQUENCE (SIZE (1..maxNrofCellMeas)) OF CellsToAddMod

-- TAG-PCI-RANGEINDEX-STOP
-- TAG-PCI-RANGEINDEXLIST-START
PCI-RangeIndexList ::= SEQUENCE (SIZE (1..maxNrofPCI-Ranges)) OF PCI-RangeIndex

-- TAG-PCI-RANGE-STOP
-- TAG-PCI-RANGEELEMENT-START
PCI-RangeElement ::= SEQUENCE {
   pci-RangeIndex [0] PCI-RangeIndex,
   pci-Range [1] PCI-Range
}

SSB-MTC3-r16 ::= SEQUENCE {
   periodicityAndOffset-r16 [0] EXPLICIT CHOICE {
      sf5-r16 [0] INTEGER (0..4),
      sf10-r16 [1] INTEGER (0..9),
      sf20-r16 [2] INTEGER (0..19),
      sf40-r16 [3] INTEGER (0..39),
      sf80-r16 [4] INTEGER (0..79),
      sf160-r16 [5] INTEGER (0..159),
      sf320-r16 [6] INTEGER (0..319),
      sf640-r16 [7] INTEGER (0..639),
      sf1280-r16 [8] INTEGER (0..1279)
   },
   duration-r16 [1] ENUMERATED { sf1(0), sf2(1), sf3(2), sf4(3), sf5(4) },
   pci-List-r16 [2] SEQUENCE (SIZE (1..maxNrofPCIsPerSMTC)) OF PhysCellId OPTIONAL, -- Need M
   ssb-ToMeasure-r16 [3] EXPLICIT CHOICE {
      release [0] NULL,
      setup [1] EXPLICIT SSB-ToMeasure
   } OPTIONAL -- Need M
}

SSB-MTC3List-r16 ::= SEQUENCE (SIZE (1..4)) OF SSB-MTC3-r16

RMTC-Config-r16 ::= SEQUENCE {
   rmtc-Periodicity-r16 [0] ENUMERATED { ms40(0), ms80(1), ms160(2), ms320(3), 
      ms640(4) },
   rmtc-SubframeOffset-r16 [1] INTEGER (0..639) OPTIONAL, -- Need M
   measDurationSymbols-r16 [2] ENUMERATED { sym1(0), sym14or12(1), sym28or24(2)
      , sym42or36(3), sym70or60(4) },
   rmtc-Frequency-r16 [3] ARFCN-ValueNR,
   ref-SCS-CP-r16 [4] ENUMERATED { kHz15(0), kHz30(1), kHz60-NCP(2), 
      kHz60-ECP(3) },
   ...,
   [[
      rmtc-Bandwidth-r17 [5] ENUMERATED { mhz100(0), mhz400(1), mhz800(2), 
         mhz1600(3), mhz2000(4) } OPTIONAL,
      measDurationSymbols-v1700 [6] ENUMERATED { sym140(0), sym560(1), 
         sym1120(2) } OPTIONAL,
      ref-SCS-CP-v1700 [7] ENUMERATED { kHz120(0), kHz480(1), kHz960(2) }
          OPTIONAL,
      tci-StateInfo-r17 [8] SEQUENCE {
         tci-StateId-r17 [0] TCI-StateId,
         ref-ServCellId-r17 [1] ServCellIndex OPTIONAL -- Need R
      } OPTIONAL
   ]],
   [[
      ref-BWPId-r17 [9] BWP-Id OPTIONAL
   ]]
}

CellsToAddModExt-v1710 ::= SEQUENCE {
   ntn-PolarizationDL-r17 [0] ENUMERATED { rhcp(0), lhcp(1), linear(2) }
       OPTIONAL, -- Need R
   ntn-PolarizationUL-r17 [1] ENUMERATED { rhcp(0), lhcp(1), linear(2) }
       OPTIONAL -- Need R
}

CellsToAddModListExt-v1710 ::= SEQUENCE (SIZE (1..maxNrofCellMeas)) OF CellsToAddModExt-v1710

-- TAG-MEASOBJECTID-STOP
-- TAG-MEASOBJECTNR-START
MeasObjectNR ::= SEQUENCE {
   ssbFrequency [0] ARFCN-ValueNR OPTIONAL, -- Cond SSBorAssociatedSSB
   ssbSubcarrierSpacing [1] SubcarrierSpacing OPTIONAL, -- Cond SSBorAssociatedSSB
   smtc1 [2] SSB-MTC OPTIONAL, -- Cond SSBorAssociatedSSB
   smtc2 [3] SSB-MTC2 OPTIONAL, -- Cond IntraFreqConnected
   refFreqCSI-RS [4] ARFCN-ValueNR OPTIONAL, -- Cond CSI-RS
   referenceSignalConfig [5] ReferenceSignalConfig,
   absThreshSS-BlocksConsolidation [6] ThresholdNR OPTIONAL, -- Need R
   absThreshCSI-RS-Consolidation [7] ThresholdNR OPTIONAL, -- Need R
   nrofSS-BlocksToAverage [8] INTEGER (2..maxNrofSS-BlocksToAverage) OPTIONAL, -- Need R
   nrofCSI-RS-ResourcesToAverage [9] INTEGER (2..maxNrofCSI-RS-ResourcesToAverage) OPTIONAL, -- Need R
   quantityConfigIndex [10] INTEGER (1..maxNrofQuantityConfig),
   offsetMO [11] Q-OffsetRangeList,
   cellsToRemoveList [12] PCI-List OPTIONAL, -- Need N
   cellsToAddModList [13] CellsToAddModList OPTIONAL, -- Need N
   excludedCellsToRemoveList [14] PCI-RangeIndexList OPTIONAL, -- Need N
   excludedCellsToAddModList [15] SEQUENCE (SIZE (1..maxNrofPCI-Ranges)) OF PCI-RangeElement
       OPTIONAL, -- Need N
   allowedCellsToRemoveList [16] PCI-RangeIndexList OPTIONAL, -- Need N
   allowedCellsToAddModList [17] SEQUENCE (SIZE (1..maxNrofPCI-Ranges)) OF PCI-RangeElement
       OPTIONAL,
   ...,
   [[
      freqBandIndicatorNR [18] FreqBandIndicatorNR OPTIONAL,
      measCycleSCell [19] ENUMERATED { sf160(0), sf256(1), sf320(2), sf512(3), 
         sf640(4), sf1024(5), sf1280(6) } OPTIONAL
   ]],
   [[
      smtc3list-r16 [20] SSB-MTC3List-r16 OPTIONAL,
      rmtc-Config-r16 [21] EXPLICIT CHOICE {
         release [0] NULL,
         setup [1] EXPLICIT RMTC-Config-r16
      } OPTIONAL,
      t312-r16 [22] EXPLICIT CHOICE {
         release [0] NULL,
         setup [1] EXPLICIT T312-r16
      } OPTIONAL
   ]],
   [[
      associatedMeasGapSSB-r17 [23] MeasGapId-r17 OPTIONAL,
      associatedMeasGapCSIRS-r17 [24] MeasGapId-r17 OPTIONAL,
      smtc4list-r17 [25] SSB-MTC4List-r17 OPTIONAL,
      measCyclePSCell-r17 [26] ENUMERATED { ms160(0), ms256(1), ms320(2), 
         ms512(3), ms640(4), ms1024(5), ms1280(6), spare1(7) } OPTIONAL,
      cellsToAddModListExt-v1710 [27] CellsToAddModListExt-v1710 OPTIONAL
   ]],
   [[
      associatedMeasGapSSB2-v1720 [28] MeasGapId-r17 OPTIONAL,
      associatedMeasGapCSIRS2-v1720 [29] MeasGapId-r17 OPTIONAL
   ]]
}

EUTRA-CellIndexList ::= SEQUENCE (SIZE (1..maxCellMeasEUTRA)) OF EUTRA-CellIndex

EUTRA-Cell ::= SEQUENCE {
   cellIndexEUTRA [0] EUTRA-CellIndex,
   physCellId [1] EUTRA-PhysCellId,
   cellIndividualOffset [2] EUTRA-Q-OffsetRange
}

EUTRA-ExcludedCell ::= SEQUENCE {
   cellIndexEUTRA [0] EUTRA-CellIndex,
   physCellIdRange [1] EUTRA-PhysCellIdRange
}

-- TAG-MEASOBJECTCLI-STOP
-- TAG-MEASOBJECTEUTRA-START
MeasObjectEUTRA ::= SEQUENCE {
   carrierFreq [0] ARFCN-ValueEUTRA,
   allowedMeasBandwidth [1] EUTRA-AllowedMeasBandwidth,
   cellsToRemoveListEUTRAN [2] EUTRA-CellIndexList OPTIONAL, -- Need N
   cellsToAddModListEUTRAN [3] SEQUENCE (SIZE (1..maxCellMeasEUTRA)) OF EUTRA-Cell OPTIONAL, -- Need N
   excludedCellsToRemoveListEUTRAN [4] EUTRA-CellIndexList OPTIONAL, -- Need N
   excludedCellsToAddModListEUTRAN [5] SEQUENCE (SIZE (1..maxCellMeasEUTRA)) OF 
      EUTRA-ExcludedCell OPTIONAL, -- Need N
   eutra-PresenceAntennaPort1 [6] EUTRA-PresenceAntennaPort1,
   eutra-Q-OffsetRange [7] EUTRA-Q-OffsetRange OPTIONAL, -- Need R
   widebandRSRQ-Meas [8] BOOLEAN,
   ...,
   [[
      associatedMeasGap-r17 [9] MeasGapId-r17 OPTIONAL
   ]]
}

UTRA-FDD-CellIndexList-r16 ::= SEQUENCE (SIZE (1..maxCellMeasUTRA-FDD-r16)) OF UTRA-FDD-CellIndex-r16

CellsToAddModUTRA-FDD-r16 ::= SEQUENCE {
   cellIndexUTRA-FDD-r16 [0] UTRA-FDD-CellIndex-r16,
   physCellId-r16 [1] PhysCellIdUTRA-FDD-r16
}

CellsToAddModListUTRA-FDD-r16 ::= SEQUENCE (SIZE (1..maxCellMeasUTRA-FDD-r16)) OF 
   CellsToAddModUTRA-FDD-r16

-- TAG-MEASOBJECTTOADDMODLIST-STOP
-- TAG-MEASOBJECTUTRA-FDD-START
MeasObjectUTRA-FDD-r16 ::= SEQUENCE {
   carrierFreq-r16 [0] ARFCN-ValueUTRA-FDD-r16,
   utra-FDD-Q-OffsetRange-r16 [1] UTRA-FDD-Q-OffsetRange-r16 OPTIONAL, -- Need R
   cellsToRemoveList-r16 [2] UTRA-FDD-CellIndexList-r16 OPTIONAL, -- Need N
   cellsToAddModList-r16 [3] CellsToAddModListUTRA-FDD-r16 OPTIONAL,
   ...
}

Tx-PoolMeasList-r16 ::= SEQUENCE (SIZE (1..maxNrofSL-PoolToMeasureNR-r16)) OF SL-ResourcePoolID-r16

-- TAG-MEASOBJECTNR-STOP
-- TAG-MEASOBJECTNR-SL-START
MeasObjectNR-SL-r16 ::= SEQUENCE {
   tx-PoolMeasToRemoveList-r16 [0] Tx-PoolMeasList-r16 OPTIONAL, -- Need N
   tx-PoolMeasToAddModList-r16 [1] Tx-PoolMeasList-r16 OPTIONAL -- Need N
}

SRS-ResourceConfigCLI-r16 ::= SEQUENCE {
   srs-Resource-r16 [0] SRS-Resource,
   srs-SCS-r16 [1] SubcarrierSpacing,
   refServCellIndex-r16 [2] ServCellIndex OPTIONAL, -- Need S
   refBWP-r16 [3] BWP-Id,
   ...
}

SRS-ResourceListConfigCLI-r16 ::= SEQUENCE (SIZE (1..maxNrofCLI-SRS-Resources-r16)) OF 
   SRS-ResourceConfigCLI-r16

RSSI-PeriodicityAndOffset-r16 ::= CHOICE {
   sl10 [0] INTEGER (0..9),
   sl20 [1] INTEGER (0..19),
   sl40 [2] INTEGER (0..39),
   sl80 [3] INTEGER (0..79),
   sl160 [4] INTEGER (0..159),
   sl320 [5] INTEGER (0..319),
   s1640 [6] INTEGER (0..639),
   ...
}

RSSI-ResourceConfigCLI-r16 ::= SEQUENCE {
   rssi-ResourceId-r16 [0] RSSI-ResourceId-r16,
   rssi-SCS-r16 [1] SubcarrierSpacing,
   startPRB-r16 [2] INTEGER (0..2169),
   nrofPRBs-r16 [3] INTEGER (4..maxNrofPhysicalResourceBlocksPlus1),
   startPosition-r16 [4] INTEGER (0..13),
   nrofSymbols-r16 [5] INTEGER (1..14),
   rssi-PeriodicityAndOffset-r16 [6] EXPLICIT RSSI-PeriodicityAndOffset-r16,
   refServCellIndex-r16 [7] ServCellIndex OPTIONAL,
   ...
}

RSSI-ResourceListConfigCLI-r16 ::= SEQUENCE (SIZE (1..maxNrofCLI-RSSI-Resources-r16)) OF 
   RSSI-ResourceConfigCLI-r16

CLI-ResourceConfig-r16 ::= SEQUENCE {
   srs-ResourceConfig-r16 [0] EXPLICIT CHOICE {
      release [0] NULL,
      setup [1] EXPLICIT SRS-ResourceListConfigCLI-r16
   } OPTIONAL, -- Need M
   rssi-ResourceConfig-r16 [1] EXPLICIT CHOICE {
      release [0] NULL,
      setup [1] EXPLICIT RSSI-ResourceListConfigCLI-r16
   } OPTIONAL -- Need M
}

-- TAG-MEASIDTOADDMODLIST-STOP
-- TAG-MEASOBJECTCLI-START
MeasObjectCLI-r16 ::= SEQUENCE {
   cli-ResourceConfig-r16 [0] CLI-ResourceConfig-r16,
   ...
}

-- TAG-MEASOBJECTNR-SL-STOP
-- TAG-MEASOBJECTRXTXDIFF-START
MeasObjectRxTxDiff-r17 ::= SEQUENCE {
   dl-Ref-r17 [0] EXPLICIT CHOICE {
      prs-Ref-r17 [0] NULL,
      csi-RS-Ref-r17 [1] NULL,
      ...
   } OPTIONAL,
   ...
}

MeasObjectToAddMod ::= SEQUENCE {
   measObjectId [0] MeasObjectId,
   measObject [1] EXPLICIT CHOICE {
      measObjectNR [0] MeasObjectNR,
      ...,
      measObjectEUTRA [1] MeasObjectEUTRA,
      measObjectUTRA-FDD-r16 [2] MeasObjectUTRA-FDD-r16,
      measObjectNR-SL-r16 [3] MeasObjectNR-SL-r16,
      measObjectCLI-r16 [4] MeasObjectCLI-r16,
      measObjectRxTxDiff-r17 [5] MeasObjectRxTxDiff-r17,
      measObjectRelay-r17 [6] SL-MeasObject-r16
   }
}

-- TAG-MEASOBJECTRXTXDIFF-STOP
-- TAG-MEASOBJECTTOADDMODLIST-START
MeasObjectToAddModList ::= SEQUENCE (SIZE (1..maxNrofObjectId)) OF MeasObjectToAddMod

ReportConfigToRemoveList ::= SEQUENCE (SIZE (1..maxReportConfigId)) OF ReportConfigId

MeasReportQuantity ::= SEQUENCE {
   rsrp [0] BOOLEAN,
   rsrq [1] BOOLEAN,
   sinr [2] BOOLEAN
}

MeasRSSI-ReportConfig-r16 ::= SEQUENCE {
   channelOccupancyThreshold-r16 [0] RSSI-Range-r16 OPTIONAL -- Need R
}

-- TAG-AREACONFIGURATION-STOP
-- TAG-BTNAMELIST-START
BT-NameList-r16 ::= SEQUENCE (SIZE (1..maxBT-Name-r16)) OF BT-Name-r16

-- TAG-VISITEDCELLINFOLIST-STOP
-- TAG-WLANNAMELIST-START
WLAN-NameList-r16 ::= SEQUENCE (SIZE (1..maxWLAN-Name-r16)) OF WLAN-Name-r16

-- TAG-RRC-TRANSACTIONIDENTIFIER-STOP
-- TAG-SENSORNAMELIST-START
Sensor-NameList-r16 ::= SEQUENCE {
   measUncomBarPre-r16 [0] ENUMERATED { true(0) } OPTIONAL, -- Need R
   measUeSpeed [1] ENUMERATED { true(0) } OPTIONAL, -- Need R
   measUeOrientation [2] ENUMERATED { true(0) } OPTIONAL -- Need R
}

-- TAG-UE-TIMERSANDCONSTANTSREMOTEUE-STOP
-- TAG-ULDELAYVALUECONFIG-START
UL-DelayValueConfig-r16 ::= SEQUENCE {
   delay-DRBlist-r16 [0] SEQUENCE (SIZE (1..maxDRB)) OF DRB-Identity
}

ExcessDelay-DRB-IdentityInfo-r17 ::= SEQUENCE {
   drb-IdentityList [0] SEQUENCE (SIZE (1..maxDRB)) OF DRB-Identity,
   delayThreshold [1] ENUMERATED { ms0dot25(0), ms0dot5(1), ms1(2), ms2(3), 
      ms4(4), ms5(5), ms10(6), ms20(7), ms30(8), ms40(9), ms50(10), ms60(11), 
      ms70(12), ms80(13), ms90(14), ms100(15), ms150(16), ms300(17), ms500(18)
       }
}

-- TAG-ULDELAYVALUECONFIG-STOP
-- TAG-ULEXCESSDELAYCONFIG-START
UL-ExcessDelayConfig-r17 ::= SEQUENCE {
   excessDelay-DRBlist-r17 [0] SEQUENCE (SIZE (1..maxDRB)) OF 
      ExcessDelay-DRB-IdentityInfo-r17
}

PeriodicalReportConfig ::= SEQUENCE {
   rsType [0] NR-RS-Type,
   reportInterval [1] ReportInterval,
   reportAmount [2] ENUMERATED { r1(0), r2(1), r4(2), r8(3), r16(4), r32(5), 
      r64(6), infinity(7) },
   reportQuantityCell [3] MeasReportQuantity,
   maxReportCells [4] INTEGER (1..maxCellReport),
   reportQuantityRS-Indexes [5] MeasReportQuantity OPTIONAL, -- Need R
   maxNrofRS-IndexesToReport [6] INTEGER (1..maxNrofIndexesToReport) OPTIONAL, -- Need R
   includeBeamMeasurements [7] BOOLEAN,
   useAllowedCellList [8] BOOLEAN,
   ...,
   [[
      measRSSI-ReportConfig-r16 [9] MeasRSSI-ReportConfig-r16 OPTIONAL,
      includeCommonLocationInfo-r16 [10] ENUMERATED { true(0) } OPTIONAL,
      includeBT-Meas-r16 [11] EXPLICIT CHOICE {
         release [0] NULL,
         setup [1] EXPLICIT BT-NameList-r16
      } OPTIONAL,
      includeWLAN-Meas-r16 [12] EXPLICIT CHOICE {
         release [0] NULL,
         setup [1] EXPLICIT WLAN-NameList-r16
      } OPTIONAL,
      includeSensor-Meas-r16 [13] EXPLICIT CHOICE {
         release [0] NULL,
         setup [1] EXPLICIT Sensor-NameList-r16
      } OPTIONAL,
      ul-DelayValueConfig-r16 [14] EXPLICIT CHOICE {
         release [0] NULL,
         setup [1] EXPLICIT UL-DelayValueConfig-r16
      } OPTIONAL,
      reportAddNeighMeas-r16 [15] ENUMERATED { setup(0) } OPTIONAL
   ]],
   [[
      ul-ExcessDelayConfig-r17 [16] EXPLICIT CHOICE {
         release [0] NULL,
         setup [1] EXPLICIT UL-ExcessDelayConfig-r17
      } OPTIONAL,
      coarseLocationRequest-r17 [17] ENUMERATED { true(0) } OPTIONAL,
      reportQuantityRelay-r17 [18] EXPLICIT SL-MeasReportQuantity-r16 OPTIONAL
   ]]
}

MeasTriggerQuantity ::= CHOICE {
   rsrp [0] RSRP-Range,
   rsrq [1] RSRQ-Range,
   sinr [2] SINR-Range
}

MeasTriggerQuantityOffset ::= CHOICE {
   rsrp [0] INTEGER (-30..30),
   rsrq [1] INTEGER (-30..30),
   sinr [2] INTEGER (-30..30)
}

EventTriggerConfig ::= SEQUENCE {
   eventId [0] EXPLICIT CHOICE {
      eventA1 [0] SEQUENCE {
         a1-Threshold [0] EXPLICIT MeasTriggerQuantity,
         reportOnLeave [1] BOOLEAN,
         hysteresis [2] Hysteresis,
         timeToTrigger [3] TimeToTrigger
      },
      eventA2 [1] SEQUENCE {
         a2-Threshold [0] EXPLICIT MeasTriggerQuantity,
         reportOnLeave [1] BOOLEAN,
         hysteresis [2] Hysteresis,
         timeToTrigger [3] TimeToTrigger
      },
      eventA3 [2] SEQUENCE {
         a3-Offset [0] EXPLICIT MeasTriggerQuantityOffset,
         reportOnLeave [1] BOOLEAN,
         hysteresis [2] Hysteresis,
         timeToTrigger [3] TimeToTrigger,
         useAllowedCellList [4] BOOLEAN
      },
      eventA4 [3] SEQUENCE {
         a4-Threshold [0] EXPLICIT MeasTriggerQuantity,
         reportOnLeave [1] BOOLEAN,
         hysteresis [2] Hysteresis,
         timeToTrigger [3] TimeToTrigger,
         useAllowedCellList [4] BOOLEAN
      },
      eventA5 [4] SEQUENCE {
         a5-Threshold1 [0] EXPLICIT MeasTriggerQuantity,
         a5-Threshold2 [1] EXPLICIT MeasTriggerQuantity,
         reportOnLeave [2] BOOLEAN,
         hysteresis [3] Hysteresis,
         timeToTrigger [4] TimeToTrigger,
         useAllowedCellList [5] BOOLEAN
      },
      eventA6 [5] SEQUENCE {
         a6-Offset [0] EXPLICIT MeasTriggerQuantityOffset,
         reportOnLeave [1] BOOLEAN,
         hysteresis [2] Hysteresis,
         timeToTrigger [3] TimeToTrigger,
         useAllowedCellList [4] BOOLEAN
      },
      ...,
      eventX1-r17 [6] SEQUENCE {
         x1-Threshold1-Relay-r17 [0] EXPLICIT SL-MeasTriggerQuantity-r16,
         x1-Threshold2-r17 [1] EXPLICIT MeasTriggerQuantity,
         reportOnLeave-r17 [2] BOOLEAN,
         hysteresis-r17 [3] Hysteresis,
         timeToTrigger-r17 [4] TimeToTrigger,
         useAllowedCellList-r17 [5] BOOLEAN
      },
      eventX2-r17 [7] SEQUENCE {
         x2-Threshold-Relay-r17 [0] EXPLICIT SL-MeasTriggerQuantity-r16,
         reportOnLeave-r17 [1] BOOLEAN,
         hysteresis-r17 [2] Hysteresis,
         timeToTrigger-r17 [3] TimeToTrigger
      },
      eventD1-r17 [8] SEQUENCE {
         distanceThreshFromReference1-r17 [0] INTEGER (1..65525),
         distanceThreshFromReference2-r17 [1] INTEGER (1..65525),
         referenceLocation1-r17 [2] ReferenceLocation-r17,
         referenceLocation2-r17 [3] ReferenceLocation-r17,
         reportOnLeave-r17 [4] BOOLEAN,
         hysteresisLocation-r17 [5] HysteresisLocation-r17,
         timeToTrigger-r17 [6] TimeToTrigger
      }
   },
   rsType [1] NR-RS-Type,
   reportInterval [2] ReportInterval,
   reportAmount [3] ENUMERATED { r1(0), r2(1), r4(2), r8(3), r16(4), r32(5), 
      r64(6), infinity(7) },
   reportQuantityCell [4] MeasReportQuantity,
   maxReportCells [5] INTEGER (1..maxCellReport),
   reportQuantityRS-Indexes [6] MeasReportQuantity OPTIONAL, -- Need R
   maxNrofRS-IndexesToReport [7] INTEGER (1..maxNrofIndexesToReport) OPTIONAL, -- Need R
   includeBeamMeasurements [8] BOOLEAN,
   reportAddNeighMeas [9] ENUMERATED { setup(0) } OPTIONAL,
   ...,
   [[
      measRSSI-ReportConfig-r16 [10] MeasRSSI-ReportConfig-r16 OPTIONAL,
      useT312-r16 [11] BOOLEAN OPTIONAL,
      includeCommonLocationInfo-r16 [12] ENUMERATED { true(0) } OPTIONAL,
      includeBT-Meas-r16 [13] EXPLICIT CHOICE {
         release [0] NULL,
         setup [1] EXPLICIT BT-NameList-r16
      } OPTIONAL,
      includeWLAN-Meas-r16 [14] EXPLICIT CHOICE {
         release [0] NULL,
         setup [1] EXPLICIT WLAN-NameList-r16
      } OPTIONAL,
      includeSensor-Meas-r16 [15] EXPLICIT CHOICE {
         release [0] NULL,
         setup [1] EXPLICIT Sensor-NameList-r16
      } OPTIONAL
   ]],
   [[
      coarseLocationRequest-r17 [16] ENUMERATED { true(0) } OPTIONAL,
      reportQuantityRelay-r17 [17] EXPLICIT SL-MeasReportQuantity-r16 OPTIONAL
   ]]
}

ReportCGI ::= SEQUENCE {
   cellForWhichToReportCGI [0] PhysCellId,
   ...,
   [[
      useAutonomousGaps-r16 [1] ENUMERATED { setup(0) } OPTIONAL
   ]]
}

ReportSFTD-NR ::= SEQUENCE {
   reportSFTD-Meas [0] BOOLEAN,
   reportRSRP [1] BOOLEAN,
   ...,
   [[
      reportSFTD-NeighMeas [2] ENUMERATED { true(0) } OPTIONAL,
      drx-SFTD-NeighMeas [3] ENUMERATED { true(0) } OPTIONAL,
      cellsForWhichToReportSFTD [4] SEQUENCE (SIZE (1..maxCellSFTD)) OF PhysCellId OPTIONAL
   ]]
}

CondTriggerConfig-r16 ::= SEQUENCE {
   condEventId [0] EXPLICIT CHOICE {
      condEventA3 [0] SEQUENCE {
         a3-Offset [0] EXPLICIT MeasTriggerQuantityOffset,
         hysteresis [1] Hysteresis,
         timeToTrigger [2] TimeToTrigger
      },
      condEventA5 [1] SEQUENCE {
         a5-Threshold1 [0] EXPLICIT MeasTriggerQuantity,
         a5-Threshold2 [1] EXPLICIT MeasTriggerQuantity,
         hysteresis [2] Hysteresis,
         timeToTrigger [3] TimeToTrigger
      },
      ...,
      condEventA4-r17 [2] SEQUENCE {
         a4-Threshold-r17 [0] EXPLICIT MeasTriggerQuantity,
         hysteresis-r17 [1] Hysteresis,
         timeToTrigger-r17 [2] TimeToTrigger
      },
      condEventD1-r17 [3] SEQUENCE {
         distanceThreshFromReference1-r17 [0] INTEGER (0..65525),
         distanceThreshFromReference2-r17 [1] INTEGER (0..65525),
         referenceLocation1-r17 [2] ReferenceLocation-r17,
         referenceLocation2-r17 [3] ReferenceLocation-r17,
         hysteresisLocation-r17 [4] HysteresisLocation-r17,
         timeToTrigger-r17 [5] TimeToTrigger
      },
      condEventT1-r17 [4] SEQUENCE {
         t1-Threshold-r17 [0] INTEGER (0..549755813887),
         duration-r17 [1] INTEGER (1..6000)
      }
   },
   rsType-r16 [1] NR-RS-Type,
   ...
}

CLI-PeriodicalReportConfig-r16 ::= SEQUENCE {
   reportInterval-r16 [0] ReportInterval,
   reportAmount-r16 [1] ENUMERATED { r1(0), r2(1), r4(2), r8(3), r16(4), r32(5)
      , r64(6), infinity(7) },
   reportQuantityCLI-r16 [2] MeasReportQuantityCLI-r16,
   maxReportCLI-r16 [3] INTEGER (1..maxCLI-Report-r16),
   ...
}

MeasTriggerQuantityCLI-r16 ::= CHOICE {
   srs-RSRP-r16 [0] SRS-RSRP-Range-r16,
   cli-RSSI-r16 [1] CLI-RSSI-Range-r16
}

CLI-EventTriggerConfig-r16 ::= SEQUENCE {
   eventId-r16 [0] EXPLICIT CHOICE {
      eventI1-r16 [0] SEQUENCE {
         i1-Threshold-r16 [0] EXPLICIT MeasTriggerQuantityCLI-r16,
         reportOnLeave-r16 [1] BOOLEAN,
         hysteresis-r16 [2] Hysteresis,
         timeToTrigger-r16 [3] TimeToTrigger
      },
      ...
   },
   reportInterval-r16 [1] ReportInterval,
   reportAmount-r16 [2] ENUMERATED { r1(0), r2(1), r4(2), r8(3), r16(4), r32(5)
      , r64(6), infinity(7) },
   maxReportCLI-r16 [3] INTEGER (1..maxCLI-Report-r16),
   ...
}

RxTxPeriodical-r17 ::= SEQUENCE {
   rxTxReportInterval-r17 [0] RxTxReportInterval-r17 OPTIONAL, -- Need R
   reportAmount-r17 [1] ENUMERATED { r1(0), infinity(1), spare6(2), spare5(3), 
      spare4(4), spare3(5), spare2(6), spare1(7) },
   ...
}

-- TAG-REPORTCONFIGINTERRAT-STOP
-- TAG-REPORTCONFIGNR-START
ReportConfigNR ::= SEQUENCE {
   reportType [0] EXPLICIT CHOICE {
      periodical [0] PeriodicalReportConfig,
      eventTriggered [1] EventTriggerConfig,
      ...,
      reportCGI [2] ReportCGI,
      reportSFTD [3] ReportSFTD-NR,
      condTriggerConfig-r16 [4] CondTriggerConfig-r16,
      cli-Periodical-r16 [5] CLI-PeriodicalReportConfig-r16,
      cli-EventTriggered-r16 [6] CLI-EventTriggerConfig-r16,
      rxTxPeriodical-r17 [7] RxTxPeriodical-r17
   }
}

MeasReportQuantityUTRA-FDD-r16 ::= SEQUENCE {
   cpich-RSCP [0] BOOLEAN,
   cpich-EcN0 [1] BOOLEAN
}

PeriodicalReportConfigInterRAT ::= SEQUENCE {
   reportInterval [0] ReportInterval,
   reportAmount [1] ENUMERATED { r1(0), r2(1), r4(2), r8(3), r16(4), r32(5), 
      r64(6), infinity(7) },
   reportQuantity [2] MeasReportQuantity,
   maxReportCells [3] INTEGER (1..maxCellReport),
   ...,
   [[
      reportQuantityUTRA-FDD-r16 [4] MeasReportQuantityUTRA-FDD-r16 OPTIONAL
   ]],
   [[
      includeCommonLocationInfo-r16 [5] ENUMERATED { true(0) } OPTIONAL,
      includeBT-Meas-r16 [6] EXPLICIT CHOICE {
         release [0] NULL,
         setup [1] EXPLICIT BT-NameList-r16
      } OPTIONAL,
      includeWLAN-Meas-r16 [7] EXPLICIT CHOICE {
         release [0] NULL,
         setup [1] EXPLICIT WLAN-NameList-r16
      } OPTIONAL,
      includeSensor-Meas-r16 [8] EXPLICIT CHOICE {
         release [0] NULL,
         setup [1] EXPLICIT Sensor-NameList-r16
      } OPTIONAL
   ]],
   [[
      reportQuantityRelay-r17 [9] EXPLICIT SL-MeasReportQuantity-r16 OPTIONAL
   ]]
}

-- TAG-MEASRESULTSSL-STOP
-- TAG-MEASTRIGGERQUANTITYEUTRA-START
MeasTriggerQuantityEUTRA ::= CHOICE {
   rsrp [0] RSRP-RangeEUTRA,
   rsrq [1] RSRQ-RangeEUTRA,
   sinr [2] SINR-RangeEUTRA
}

MeasTriggerQuantityUTRA-FDD-r16 ::= CHOICE {
   utra-FDD-RSCP-r16 [0] INTEGER (-5..91),
   utra-FDD-EcN0-r16 [1] INTEGER (0..49)
}

EventTriggerConfigInterRAT ::= SEQUENCE {
   eventId [0] EXPLICIT CHOICE {
      eventB1 [0] SEQUENCE {
         b1-ThresholdEUTRA [0] EXPLICIT MeasTriggerQuantityEUTRA,
         reportOnLeave [1] BOOLEAN,
         hysteresis [2] Hysteresis,
         timeToTrigger [3] TimeToTrigger,
         ...
      },
      eventB2 [1] SEQUENCE {
         b2-Threshold1 [0] EXPLICIT MeasTriggerQuantity,
         b2-Threshold2EUTRA [1] EXPLICIT MeasTriggerQuantityEUTRA,
         reportOnLeave [2] BOOLEAN,
         hysteresis [3] Hysteresis,
         timeToTrigger [4] TimeToTrigger,
         ...
      },
      ...,
      eventB1-UTRA-FDD-r16 [2] SEQUENCE {
         b1-ThresholdUTRA-FDD-r16 [0] EXPLICIT MeasTriggerQuantityUTRA-FDD-r16,
         reportOnLeave-r16 [1] BOOLEAN,
         hysteresis-r16 [2] Hysteresis,
         timeToTrigger-r16 [3] TimeToTrigger,
         ...
      },
      eventB2-UTRA-FDD-r16 [3] SEQUENCE {
         b2-Threshold1-r16 [0] EXPLICIT MeasTriggerQuantity,
         b2-Threshold2UTRA-FDD-r16 [1] EXPLICIT MeasTriggerQuantityUTRA-FDD-r16
            ,
         reportOnLeave-r16 [2] BOOLEAN,
         hysteresis-r16 [3] Hysteresis,
         timeToTrigger-r16 [4] TimeToTrigger,
         ...
      },
      eventY1-Relay-r17 [4] SEQUENCE {
         y1-Threshold1-r17 [0] EXPLICIT MeasTriggerQuantity,
         y1-Threshold2-Relay-r17 [1] EXPLICIT SL-MeasTriggerQuantity-r16,
         reportOnLeave-r17 [2] BOOLEAN,
         hysteresis-r17 [3] Hysteresis,
         timeToTrigger-r17 [4] TimeToTrigger,
         ...
      },
      eventY2-Relay-r17 [5] SEQUENCE {
         y2-Threshold-Relay-r17 [0] EXPLICIT SL-MeasTriggerQuantity-r16,
         reportOnLeave-r17 [1] BOOLEAN,
         hysteresis-r17 [2] Hysteresis,
         timeToTrigger-r17 [3] TimeToTrigger,
         ...
      }
   },
   rsType [1] NR-RS-Type,
   reportInterval [2] ReportInterval,
   reportAmount [3] ENUMERATED { r1(0), r2(1), r4(2), r8(3), r16(4), r32(5), 
      r64(6), infinity(7) },
   reportQuantity [4] MeasReportQuantity,
   maxReportCells [5] INTEGER (1..maxCellReport),
   ...,
   [[
      reportQuantityUTRA-FDD-r16 [6] MeasReportQuantityUTRA-FDD-r16 OPTIONAL
   ]],
   [[
      includeCommonLocationInfo-r16 [7] ENUMERATED { true(0) } OPTIONAL,
      includeBT-Meas-r16 [8] EXPLICIT CHOICE {
         release [0] NULL,
         setup [1] EXPLICIT BT-NameList-r16
      } OPTIONAL,
      includeWLAN-Meas-r16 [9] EXPLICIT CHOICE {
         release [0] NULL,
         setup [1] EXPLICIT WLAN-NameList-r16
      } OPTIONAL,
      includeSensor-Meas-r16 [10] EXPLICIT CHOICE {
         release [0] NULL,
         setup [1] EXPLICIT Sensor-NameList-r16
      } OPTIONAL
   ]],
   [[
      reportQuantityRelay-r17 [11] EXPLICIT SL-MeasReportQuantity-r16 OPTIONAL
   ]]
}

ReportCGI-EUTRA ::= SEQUENCE {
   cellForWhichToReportCGI [0] EUTRA-PhysCellId,
   ...,
   [[
      useAutonomousGaps-r16 [1] ENUMERATED { setup(0) } OPTIONAL
   ]]
}

ReportSFTD-EUTRA ::= SEQUENCE {
   reportSFTD-Meas [0] BOOLEAN,
   reportRSRP [1] BOOLEAN,
   ...
}

-- TAG-REPORTCONFIGID-STOP
-- TAG-REPORTCONFIGINTERRAT-START
ReportConfigInterRAT ::= SEQUENCE {
   reportType [0] EXPLICIT CHOICE {
      periodical [0] PeriodicalReportConfigInterRAT,
      eventTriggered [1] EventTriggerConfigInterRAT,
      reportCGI [2] ReportCGI-EUTRA,
      ...,
      reportSFTD [3] ReportSFTD-EUTRA
   }
}

MeasReportQuantity-r16 ::= SEQUENCE {
   cbr-r16 [0] BOOLEAN,
   ...
}

PeriodicalReportConfigNR-SL-r16 ::= SEQUENCE {
   reportInterval-r16 [0] ReportInterval,
   reportAmount-r16 [1] ENUMERATED { r1(0), r2(1), r4(2), r8(3), r16(4), r32(5)
      , r64(6), infinity(7) },
   reportQuantity-r16 [2] MeasReportQuantity-r16,
   ...
}

EventTriggerConfigNR-SL-r16 ::= SEQUENCE {
   eventId-r16 [0] EXPLICIT CHOICE {
      eventC1 [0] SEQUENCE {
         c1-Threshold-r16 [0] SL-CBR-r16,
         hysteresis-r16 [1] Hysteresis,
         timeToTrigger-r16 [2] TimeToTrigger
      },
      eventC2-r16 [1] SEQUENCE {
         c2-Threshold-r16 [0] SL-CBR-r16,
         hysteresis-r16 [1] Hysteresis,
         timeToTrigger-r16 [2] TimeToTrigger
      },
      ...
   },
   reportInterval-r16 [1] ReportInterval,
   reportAmount-r16 [2] ENUMERATED { r1(0), r2(1), r4(2), r8(3), r16(4), r32(5)
      , r64(6), infinity(7) },
   reportQuantity-r16 [3] MeasReportQuantity-r16,
   ...
}

-- TAG-REPORTCONFIGNR-STOP
-- TAG-REPORTCONFIGNR-SL-START
ReportConfigNR-SL-r16 ::= SEQUENCE {
   reportType-r16 [0] EXPLICIT CHOICE {
      periodical-r16 [0] PeriodicalReportConfigNR-SL-r16,
      eventTriggered-r16 [1] EventTriggerConfigNR-SL-r16
   }
}

ReportConfigToAddMod ::= SEQUENCE {
   reportConfigId [0] ReportConfigId,
   reportConfig [1] EXPLICIT CHOICE {
      reportConfigNR [0] ReportConfigNR,
      ...,
      reportConfigInterRAT [1] ReportConfigInterRAT,
      reportConfigNR-SL-r16 [2] ReportConfigNR-SL-r16
   }
}

-- TAG-REPORTCONFIGNR-SL-STOP
-- TAG-REPORTCONFIGTOADDMODLIST-START
ReportConfigToAddModList ::= SEQUENCE (SIZE (1..maxReportConfigId)) OF ReportConfigToAddMod

MeasIdToRemoveList ::= SEQUENCE (SIZE (1..maxNrofMeasId)) OF MeasId

MeasIdToAddMod ::= SEQUENCE {
   measId [0] MeasId,
   measObjectId [1] MeasObjectId,
   reportConfigId [2] ReportConfigId
}

-- TAG-MEASIDLECONFIG-STOP
-- TAG-MEASIDTOADDMODLIST-START
MeasIdToAddModList ::= SEQUENCE (SIZE (1..maxNrofMeasId)) OF MeasIdToAddMod

FilterConfig ::= SEQUENCE {
   filterCoefficientRSRP [0] FilterCoefficient DEFAULT fc4,
   filterCoefficientRSRQ [1] FilterCoefficient DEFAULT fc4,
   filterCoefficientRS-SINR [2] FilterCoefficient DEFAULT fc4
}

QuantityConfigRS ::= SEQUENCE {
   ssb-FilterConfig [0] FilterConfig,
   csi-RS-FilterConfig [1] FilterConfig
}

QuantityConfigNR ::= SEQUENCE {
   quantityConfigCell [0] QuantityConfigRS,
   quantityConfigRS-Index [1] QuantityConfigRS OPTIONAL -- Need M
}

QuantityConfigUTRA-FDD-r16 ::= SEQUENCE {
   filterCoefficientRSCP-r16 [0] FilterCoefficient DEFAULT fc4,
   filterCoefficientEcNO-r16 [1] FilterCoefficient DEFAULT fc4
}

FilterConfigCLI-r16 ::= SEQUENCE {
   filterCoefficientSRS-RSRP-r16 [0] FilterCoefficient DEFAULT fc4,
   filterCoefficientCLI-RSSI-r16 [1] FilterCoefficient DEFAULT fc4
}

-- TAG-Q-RXLEVMIN-STOP
-- TAG-QUANTITYCONFIG-START
QuantityConfig ::= SEQUENCE {
   quantityConfigNR-List [0] SEQUENCE (SIZE (1..maxNrofQuantityConfig)) OF QuantityConfigNR OPTIONAL,
   ...,
   [[
      quantityConfigEUTRA [1] FilterConfig OPTIONAL
   ]],
   [[
      quantityConfigUTRA-FDD-r16 [2] QuantityConfigUTRA-FDD-r16 OPTIONAL,
      quantityConfigCLI-r16 [3] FilterConfigCLI-r16 OPTIONAL
   ]]
}

GapConfig ::= SEQUENCE {
   gapOffset [0] INTEGER (0..159),
   mgl [1] ENUMERATED { ms1dot5(0), ms3(1), ms3dot5(2), ms4(3), ms5dot5(4), 
      ms6(5) },
   mgrp [2] ENUMERATED { ms20(0), ms40(1), ms80(2), ms160(3) },
   mgta [3] ENUMERATED { ms0(0), ms0dot25(1), ms0dot5(2) },
   ...,
   [[
      refServCellIndicator [4] ENUMERATED { pCell(0), pSCell(1), mcg-FR2(2) }
          OPTIONAL
   ]],
   [[
      refFR2ServCellAsyncCA-r16 [5] ServCellIndex OPTIONAL,
      mgl-r16 [6] ENUMERATED { ms10(0), ms20(1) } OPTIONAL
   ]]
}

GapConfig-r17 ::= SEQUENCE {
   measGapId-r17 [0] MeasGapId-r17,
   gapType-r17 [1] ENUMERATED { perUE(0), perFR1(1), perFR2(2) },
   gapOffset-r17 [2] INTEGER (0..159),
   mgl-r17 [3] ENUMERATED { ms1(0), ms1dot5(1), ms2(2), ms3(3), ms3dot5(4), 
      ms4(5), ms5(6), ms5dot5(7), ms6(8), ms10(9), ms20(10) },
   mgrp-r17 [4] ENUMERATED { ms20(0), ms40(1), ms80(2), ms160(3) },
   mgta-r17 [5] ENUMERATED { ms0(0), ms0dot25(1), ms0dot5(2), ms0dot75(3) },
   refServCellIndicator-r17 [6] ENUMERATED { pCell(0), pSCell(1), mcg-FR2(2) }
       OPTIONAL, -- Cond NEDCorNRDC
   refFR2-ServCellAsyncCA-r17 [7] ServCellIndex OPTIONAL, -- Cond AsyncCA
   preConfigInd-r17 [8] ENUMERATED { true(0) } OPTIONAL, -- Need R
   ncsgInd-r17 [9] ENUMERATED { true(0) } OPTIONAL, -- Need R
   gapAssociationPRS-r17 [10] ENUMERATED { true(0) } OPTIONAL, -- Need R
   gapSharing-r17 [11] MeasGapSharingScheme OPTIONAL, -- Need R
   gapPriority-r17 [12] GapPriority-r17 OPTIONAL,
   ...
}

PosGapConfig-r17 ::= SEQUENCE {
   measPosPreConfigGapId-r17 [0] MeasPosPreConfigGapId-r17,
   gapOffset-r17 [1] INTEGER (0..159),
   mgl-r17 [2] ENUMERATED { ms1dot5(0), ms3(1), ms3dot5(2), ms4(3), ms5dot5(4)
      , ms6(5), ms10(6), ms20(7) },
   mgrp-r17 [3] ENUMERATED { ms20(0), ms40(1), ms80(2), ms160(3) },
   mgta-r17 [4] ENUMERATED { ms0(0), ms0dot25(1), ms0dot5(2) },
   gapType-r17 [5] ENUMERATED { perUE(0), perFR1(1), perFR2(2) },
   ...
}

PosMeasGapPreConfigToAddModList-r17 ::= SEQUENCE (SIZE (1..maxNrofPreConfigPosGapId-r17)) OF 
   PosGapConfig-r17

PosMeasGapPreConfigToReleaseList-r17 ::= SEQUENCE (SIZE (1..maxNrofPreConfigPosGapId-r17)) OF 
   MeasPosPreConfigGapId-r17

-- TAG-MEASCONFIG-STOP
-- TAG-MEASGAPCONFIG-START
MeasGapConfig ::= SEQUENCE {
   gapFR2 [0] EXPLICIT CHOICE {
      release [0] NULL,
      setup [1] EXPLICIT GapConfig
   } OPTIONAL,
   ...,
   [[
      gapFR1 [1] EXPLICIT CHOICE {
         release [0] NULL,
         setup [1] EXPLICIT GapConfig
      } OPTIONAL,
      gapUE [2] EXPLICIT CHOICE {
         release [0] NULL,
         setup [1] EXPLICIT GapConfig
      } OPTIONAL
   ]],
   [[
      gapToAddModList-r17 [3] SEQUENCE (SIZE (1..maxNrofGapId-r17)) OF GapConfig-r17 OPTIONAL,
      gapToReleaseList-r17 [4] SEQUENCE (SIZE (1..maxNrofGapId-r17)) OF MeasGapId-r17 OPTIONAL,
      posMeasGapPreConfigToAddModList-r17 [5] 
         PosMeasGapPreConfigToAddModList-r17 OPTIONAL,
      posMeasGapPreConfigToReleaseList-r17 [6] 
         PosMeasGapPreConfigToReleaseList-r17 OPTIONAL
   ]]
}

-- TAG-MEASGAPID-STOP
-- TAG-MEASGAPSHARINGCONFIG-START
MeasGapSharingConfig ::= SEQUENCE {
   gapSharingFR2 [0] EXPLICIT CHOICE {
      release [0] NULL,
      setup [1] EXPLICIT MeasGapSharingScheme
   } OPTIONAL,
   ...,
   [[
      gapSharingFR1 [1] EXPLICIT CHOICE {
         release [0] NULL,
         setup [1] EXPLICIT MeasGapSharingScheme
      } OPTIONAL,
      gapSharingUE [2] EXPLICIT CHOICE {
         release [0] NULL,
         setup [1] EXPLICIT MeasGapSharingScheme
      } OPTIONAL
   ]]
}

-- TAG-MAC-CELLGROUPCONFIG-STOP
-- TAG-MEASCONFIG-START
MeasConfig ::= SEQUENCE {
   measObjectToRemoveList [0] MeasObjectToRemoveList OPTIONAL, -- Need N
   measObjectToAddModList [1] MeasObjectToAddModList OPTIONAL, -- Need N
   reportConfigToRemoveList [2] ReportConfigToRemoveList OPTIONAL, -- Need N
   reportConfigToAddModList [3] ReportConfigToAddModList OPTIONAL, -- Need N
   measIdToRemoveList [4] MeasIdToRemoveList OPTIONAL, -- Need N
   measIdToAddModList [5] MeasIdToAddModList OPTIONAL, -- Need N
   s-MeasureConfig [6] EXPLICIT CHOICE {
      ssb-RSRP [0] RSRP-Range,
      csi-RSRP [1] RSRP-Range
   } OPTIONAL, -- Need M
   quantityConfig [7] QuantityConfig OPTIONAL, -- Need M
   measGapConfig [8] MeasGapConfig OPTIONAL, -- Need M
   measGapSharingConfig [9] MeasGapSharingConfig OPTIONAL,
   ...,
   [[
      interFrequencyConfig-NoGap-r16 [10] ENUMERATED { true(0) } OPTIONAL
   ]]
}

MasterKeyUpdate ::= SEQUENCE {
   keySetChangeIndicator [0] BOOLEAN,
   nextHopChainingCount [1] NextHopChainingCount,
   nas-Container [2] OCTET STRING OPTIONAL,
   ...
}

-- TAG-MEASCONFIGAPPLAYERID-STOP
-- TAG-OTHERCONFIG-START
OtherConfig ::= SEQUENCE {
   delayBudgetReportingConfig [0] EXPLICIT CHOICE {
      release [0] NULL,
      setup [1] SEQUENCE {
         delayBudgetReportingProhibitTimer [0] ENUMERATED { s0(0), s0dot4(1), 
            s0dot8(2), s1dot6(3), s3(4), s6(5), s12(6), s30(7) }
      }
   } OPTIONAL -- Need M
}

OverheatingAssistanceConfig ::= SEQUENCE {
   overheatingIndicationProhibitTimer [0] ENUMERATED { s0(0), s0dot5(1), s1(2)
      , s2(3), s5(4), s10(5), s20(6), s30(7), s60(8), s90(9), s120(10), 
      s300(11), s600(12), spare3(13), spare2(14), spare1(15) }
}

OtherConfig-v1540 ::= SEQUENCE {
   overheatingAssistanceConfig [0] EXPLICIT CHOICE {
      release [0] NULL,
      setup [1] EXPLICIT OverheatingAssistanceConfig
   } OPTIONAL,
   ...
}

MRDC-SecondaryCellGroupConfig ::= SEQUENCE {
   mrdc-ReleaseAndAdd [0] ENUMERATED { true(0) } OPTIONAL, -- Need N
   mrdc-SecondaryCellGroup [1] EXPLICIT CHOICE {
      nr-SCG [0] OCTET STRING (CONTAINING RRCReconfiguration),
      eutra-SCG [1] OCTET STRING
   }
}

CandidateServingFreqListNR-r16 ::= SEQUENCE (SIZE (1..maxFreqIDC-r16)) OF ARFCN-ValueNR

IDC-AssistanceConfig-r16 ::= SEQUENCE {
   candidateServingFreqListNR-r16 [0] CandidateServingFreqListNR-r16 OPTIONAL,
   ...
}

DRX-PreferenceConfig-r16 ::= SEQUENCE {
   drx-PreferenceProhibitTimer-r16 [0] ENUMERATED { s0(0), s0dot5(1), s1(2), 
      s2(3), s3(4), s4(5), s5(6), s6(7), s7(8), s8(9), s9(10), s10(11), s20(12)
      , s30(13), spare2(14), spare1(15) }
}

MaxBW-PreferenceConfig-r16 ::= SEQUENCE {
   maxBW-PreferenceProhibitTimer-r16 [0] ENUMERATED { s0(0), s0dot5(1), s1(2), 
      s2(3), s3(4), s4(5), s5(6), s6(7), s7(8), s8(9), s9(10), s10(11), s20(12)
      , s30(13), spare2(14), spare1(15) }
}

MaxCC-PreferenceConfig-r16 ::= SEQUENCE {
   maxCC-PreferenceProhibitTimer-r16 [0] ENUMERATED { s0(0), s0dot5(1), s1(2), 
      s2(3), s3(4), s4(5), s5(6), s6(7), s7(8), s8(9), s9(10), s10(11), s20(12)
      , s30(13), spare2(14), spare1(15) }
}

MaxMIMO-LayerPreferenceConfig-r16 ::= SEQUENCE {
   maxMIMO-LayerPreferenceProhibitTimer-r16 [0] ENUMERATED { s0(0), s0dot5(1), 
      s1(2), s2(3), s3(4), s4(5), s5(6), s6(7), s7(8), s8(9), s9(10), s10(11), 
      s20(12), s30(13), spare2(14), spare1(15) }
}

MinSchedulingOffsetPreferenceConfig-r16 ::= SEQUENCE {
   minSchedulingOffsetPreferenceProhibitTimer-r16 [0] ENUMERATED { s0(0), 
      s0dot5(1), s1(2), s2(3), s3(4), s4(5), s5(6), s6(7), s7(8), s8(9), s9(10)
      , s10(11), s20(12), s30(13), spare2(14), spare1(15) }
}

ReleasePreferenceConfig-r16 ::= SEQUENCE {
   releasePreferenceProhibitTimer-r16 [0] ENUMERATED { s0(0), s0dot5(1), s1(2)
      , s2(3), s3(4), s4(5), s5(6), s6(7), s7(8), s8(9), s9(10), s10(11), 
      s20(12), s30(13), infinity(14), spare1(15) },
   connectedReporting [1] ENUMERATED { true(0) } OPTIONAL -- Need R
}

OtherConfig-v1610 ::= SEQUENCE {
   idc-AssistanceConfig-r16 [0] EXPLICIT CHOICE {
      release [0] NULL,
      setup [1] EXPLICIT IDC-AssistanceConfig-r16
   } OPTIONAL, -- Need M
   drx-PreferenceConfig-r16 [1] EXPLICIT CHOICE {
      release [0] NULL,
      setup [1] EXPLICIT DRX-PreferenceConfig-r16
   } OPTIONAL, -- Need M
   maxBW-PreferenceConfig-r16 [2] EXPLICIT CHOICE {
      release [0] NULL,
      setup [1] EXPLICIT MaxBW-PreferenceConfig-r16
   } OPTIONAL, -- Need M
   maxCC-PreferenceConfig-r16 [3] EXPLICIT CHOICE {
      release [0] NULL,
      setup [1] EXPLICIT MaxCC-PreferenceConfig-r16
   } OPTIONAL, -- Need M
   maxMIMO-LayerPreferenceConfig-r16 [4] EXPLICIT CHOICE {
      release [0] NULL,
      setup [1] EXPLICIT MaxMIMO-LayerPreferenceConfig-r16
   } OPTIONAL, -- Need M
   minSchedulingOffsetPreferenceConfig-r16 [5] EXPLICIT CHOICE {
      release [0] NULL,
      setup [1] EXPLICIT MinSchedulingOffsetPreferenceConfig-r16
   } OPTIONAL, -- Need M
   releasePreferenceConfig-r16 [6] EXPLICIT CHOICE {
      release [0] NULL,
      setup [1] EXPLICIT ReleasePreferenceConfig-r16
   } OPTIONAL, -- Need M
   referenceTimePreferenceReporting-r16 [7] ENUMERATED { true(0) } OPTIONAL, -- Need R
   btNameList-r16 [8] EXPLICIT CHOICE {
      release [0] NULL,
      setup [1] EXPLICIT BT-NameList-r16
   } OPTIONAL, -- Need M
   wlanNameList-r16 [9] EXPLICIT CHOICE {
      release [0] NULL,
      setup [1] EXPLICIT WLAN-NameList-r16
   } OPTIONAL, -- Need M
   sensorNameList-r16 [10] EXPLICIT CHOICE {
      release [0] NULL,
      setup [1] EXPLICIT Sensor-NameList-r16
   } OPTIONAL, -- Need M
   obtainCommonLocation-r16 [11] ENUMERATED { true(0) } OPTIONAL, -- Need R
   sl-AssistanceConfigNR-r16 [12] ENUMERATED { true(0) } OPTIONAL -- Need R
}

-- TAG-AVAILABILITYINDICATOR-STOP
-- TAG-BAPROUTINGID-START
BAP-RoutingID-r16 ::= SEQUENCE {
   bap-Address-r16 [0] BIT STRING  (SIZE (10)),
   bap-PathId-r16 [1] BIT STRING  (SIZE (10))
}

BAP-Config-r16 ::= SEQUENCE {
   bap-Address-r16 [0] BIT STRING  (SIZE (10)) OPTIONAL, -- Need M
   defaultUL-BAP-RoutingID-r16 [1] BAP-RoutingID-r16 OPTIONAL, -- Need M
   defaultUL-BH-RLC-Channel-r16 [2] BH-RLC-ChannelID-r16 OPTIONAL, -- Need M
   flowControlFeedbackType-r16 [3] ENUMERATED { perBH-RLC-Channel(0), 
      perRoutingID(1), both(2) } OPTIONAL,
   ...
}

-- TAG-EUTRA-Q-OFFSETRANGE-STOP
-- TAG-IABIPADDRESS-START
IAB-IP-Address-r16 ::= CHOICE {
   iPv4-Address-r16 [0] BIT STRING  (SIZE (32)),
   iPv6-Address-r16 [1] BIT STRING  (SIZE (128)),
   iPv6-Prefix-r16 [2] BIT STRING  (SIZE (64)),
   ...
}

IAB-IP-AddressConfiguration-r16 ::= SEQUENCE {
   iab-IP-AddressIndex-r16 [0] IAB-IP-AddressIndex-r16,
   iab-IP-Address-r16 [1] EXPLICIT IAB-IP-Address-r16 OPTIONAL, -- Need M
   iab-IP-Usage-r16 [2] IAB-IP-Usage-r16 OPTIONAL, -- Need M
   iab-donor-DU-BAP-Address-r16 [3] BIT STRING  (SIZE (10)) OPTIONAL,
   ...
}

IAB-IP-AddressConfigurationList-r16 ::= SEQUENCE {
   iab-IP-AddressToAddModList-r16 [0] SEQUENCE (SIZE (1..maxIAB-IP-Address-r16)) OF 
      IAB-IP-AddressConfiguration-r16 OPTIONAL, -- Need N
   iab-IP-AddressToReleaseList-r16 [1] SEQUENCE (SIZE (1..maxIAB-IP-Address-r16)) OF 
      IAB-IP-AddressIndex-r16 OPTIONAL,
   ...
}

CondReconfigToRemoveList-r16 ::= SEQUENCE (SIZE (1..maxNrofCondCells-r16)) OF CondReconfigId-r16

CondReconfigExecCondSCG-r17 ::= SEQUENCE (SIZE (1..2)) OF MeasId

CondReconfigToAddMod-r16 ::= SEQUENCE {
   condReconfigId-r16 [0] CondReconfigId-r16,
   condExecutionCond-r16 [1] SEQUENCE (SIZE (1..2)) OF MeasId OPTIONAL, -- Need M
   condRRCReconfig-r16 [2] OCTET STRING (CONTAINING RRCReconfiguration)
       OPTIONAL,
   ...,
   [[
      condExecutionCondSCG-r17 [3] OCTET STRING (CONTAINING 
         CondReconfigExecCondSCG-r17) OPTIONAL
   ]]
}

-- TAG-CONDRECONFIGID-STOP
-- TAG-CONDRECONFIGTOADDMODLIST-START
CondReconfigToAddModList-r16 ::= SEQUENCE (SIZE (1..maxNrofCondCells-r16)) OF 
   CondReconfigToAddMod-r16

-- TAG-CONDRECONFIGTOADDMODLIST-STOP
-- TAG-CONDITIONALRECONFIGURATION-START
ConditionalReconfiguration-r16 ::= SEQUENCE {
   attemptCondReconfig-r16 [0] ENUMERATED { true(0) } OPTIONAL, -- Cond CHO
   condReconfigToRemoveList-r16 [1] CondReconfigToRemoveList-r16 OPTIONAL, -- Need N
   condReconfigToAddModList-r16 [2] CondReconfigToAddModList-r16 OPTIONAL,
   ...
}

-- TAG-MUSIM-GAPINFO-STOP
-- TAG-NeedForGapsConfigNR-START
NeedForGapsConfigNR-r16 ::= SEQUENCE {
   requestedTargetBandFilterNR-r16 [0] SEQUENCE (SIZE (1..maxBands)) OF 
      FreqBandIndicatorNR OPTIONAL -- Need R
}

OnDemandSIB-Request-r16 ::= SEQUENCE {
   onDemandSIB-RequestProhibitTimer-r16 [0] ENUMERATED { s0(0), s0dot5(1), 
      s1(2), s2(3), s5(4), s10(5), s20(6), s30(7) }
}

SL-ConfigDedicatedEUTRA-Info-r16 ::= SEQUENCE {
   sl-ConfigDedicatedEUTRA-r16 [0] OCTET STRING OPTIONAL, -- Need M
   sl-TimeOffsetEUTRA-List-r16 [1] SEQUENCE (SIZE (8)) OF SL-TimeOffsetEUTRA-r16
       OPTIONAL -- Need M
}

MUSIM-GapAssistanceConfig-r17 ::= SEQUENCE {
   musim-GapProhibitTimer-r17 [0] ENUMERATED { s0(0), s0dot1(1), s0dot2(2), 
      s0dot3(3), s0dot4(4), s0dot5(5), s1(6), s2(7), s3(8), s4(9), s5(10), 
      s6(11), s7(12), s8(13), s9(14), s10(15) }
}

MUSIM-LeaveAssistanceConfig-r17 ::= SEQUENCE {
   musim-LeaveWithoutResponseTimer-r17 [0] ENUMERATED { ms10(0), ms20(1), 
      ms40(2), ms60(3), ms80(4), ms100(5), spare2(6), spare1(7) }
}

SuccessHO-Config-r17 ::= SEQUENCE {
   thresholdPercentageT304-r17 [0] ENUMERATED { p40(0), p60(1), p80(2), 
      spare5(3), spare4(4), spare3(5), spare2(6), spare1(7) } OPTIONAL, --Need R
   thresholdPercentageT310-r17 [1] ENUMERATED { p40(0), p60(1), p80(2), 
      spare5(3), spare4(4), spare3(5), spare2(6), spare1(7) } OPTIONAL, --Need R
   thresholdPercentageT312-r17 [2] ENUMERATED { p20(0), p40(1), p60(2), p80(3)
      , spare4(4), spare3(5), spare2(6), spare1(7) } OPTIONAL, --Need R
   sourceDAPS-FailureReporting-r17 [3] ENUMERATED { true(0) } OPTIONAL,
   ...
}

RLM-RelaxationReportingConfig-r17 ::= SEQUENCE {
   rlm-RelaxtionReportingProhibitTimer [0] ENUMERATED { s0(0), s0dot5(1), s1(2)
      , s2(3), s5(4), s10(5), s20(6), s30(7), s60(8), s90(9), s120(10), 
      s300(11), s600(12), infinity(13), spare2(14), spare1(15) }
}

BFD-RelaxationReportingConfig-r17 ::= SEQUENCE {
   bfd-RelaxtionReportingProhibitTimer [0] ENUMERATED { s0(0), s0dot5(1), s1(2)
      , s2(3), s5(4), s10(5), s20(6), s30(7), s60(8), s90(9), s120(10), 
      s300(11), s600(12), infinity(13), spare2(14), spare1(15) }
}

SCG-DeactivationPreferenceConfig-r17 ::= SEQUENCE {
   scg-DeactivationPreferenceProhibitTimer-r17 [0] ENUMERATED { s0(0), s1(1), 
      s2(2), s4(3), s8(4), s10(5), s15(6), s30(7), s60(8), s120(9), s180(10), 
      s240(11), s300(12), s600(13), s900(14), s1800(15) }
}

RRM-MeasRelaxationReportingConfig-r17 ::= SEQUENCE {
   s-SearchDeltaP-Stationary-r17 [0] ENUMERATED { dB2(0), dB3(1), dB6(2), 
      dB9(3), dB12(4), dB15(5), spare2(6), spare1(7) },
   t-SearchDeltaP-Stationary-r17 [1] ENUMERATED { s5(0), s10(1), s20(2), s30(3)
      , s60(4), s120(5), s180(6), s240(7), s300(8), spare7(9), spare6(10), 
      spare5(11), spare4(12), spare3(13), spare2(14), spare1(15) }
}

NeighbourCellInfo-r17 ::= SEQUENCE {
   epochTime-r17 [0] EpochTime-r17,
   ephemerisInfo-r17 [1] EXPLICIT EphemerisInfo-r17
}

PropDelayDiffReportConfig-r17 ::= SEQUENCE {
   threshPropDelayDiff-r17 [0] ENUMERATED { ms0dot5(0), ms1(1), ms2(2), ms3(3)
      , ms4(4), ms5(5), ms6(6), ms7(7), ms8(8), ms9(9), ms10(10), spare5(11), 
      spare4(12), spare3(13), spare2(14), spare1(15) } OPTIONAL, -- Need M
   neighCellInfoList-r17 [1] SEQUENCE (SIZE (1..maxCellNTN-r17)) OF NeighbourCellInfo-r17
       OPTIONAL -- Need M
}

OtherConfig-v1700 ::= SEQUENCE {
   ul-GapFR2-PreferenceConfig-r17 [0] ENUMERATED { true(0) } OPTIONAL, -- Need R
   musim-GapAssistanceConfig-r17 [1] EXPLICIT CHOICE {
      release [0] NULL,
      setup [1] EXPLICIT MUSIM-GapAssistanceConfig-r17
   } OPTIONAL, -- Need M
   musim-LeaveAssistanceConfig-r17 [2] EXPLICIT CHOICE {
      release [0] NULL,
      setup [1] EXPLICIT MUSIM-LeaveAssistanceConfig-r17
   } OPTIONAL, -- Need M
   successHO-Config-r17 [3] EXPLICIT CHOICE {
      release [0] NULL,
      setup [1] EXPLICIT SuccessHO-Config-r17
   } OPTIONAL, -- Need M
   maxBW-PreferenceConfigFR2-2-r17 [4] ENUMERATED { true(0) } OPTIONAL, -- Cond maxBW
   maxMIMO-LayerPreferenceConfigFR2-2-r17 [5] ENUMERATED { true(0) } OPTIONAL, -- Cond maxMIMO
   minSchedulingOffsetPreferenceConfigExt-r17 [6] ENUMERATED { true(0) }
       OPTIONAL, -- Cond minOffset
   rlm-RelaxationReportingConfig-r17 [7] EXPLICIT CHOICE {
      release [0] NULL,
      setup [1] EXPLICIT RLM-RelaxationReportingConfig-r17
   } OPTIONAL, -- Need M
   bfd-RelaxationReportingConfig-r17 [8] EXPLICIT CHOICE {
      release [0] NULL,
      setup [1] EXPLICIT BFD-RelaxationReportingConfig-r17
   } OPTIONAL, -- Need M
   scg-DeactivationPreferenceConfig-r17 [9] EXPLICIT CHOICE {
      release [0] NULL,
      setup [1] EXPLICIT SCG-DeactivationPreferenceConfig-r17
   } OPTIONAL, -- Cond SCG
   rrm-MeasRelaxationReportingConfig-r17 [10] EXPLICIT CHOICE {
      release [0] NULL,
      setup [1] EXPLICIT RRM-MeasRelaxationReportingConfig-r17
   } OPTIONAL, -- Need M
   propDelayDiffReportConfig-r17 [11] EXPLICIT CHOICE {
      release [0] NULL,
      setup [1] EXPLICIT PropDelayDiffReportConfig-r17
   } OPTIONAL -- Need M
}

SL-RemoteUE-ToAddMod-r17 ::= SEQUENCE {
   sl-L2IdentityRemote-r17 [0] SL-DestinationIdentity-r16,
   sl-SRAP-ConfigRelay-r17 [1] SL-SRAP-Config-r17 OPTIONAL,
   ...
}

-- TAG-SL-LOGICALCHANNELCONFIG-STOP
-- TAG-SL-L2RELAYUE-CONFIG-START
SL-L2RelayUE-Config-r17 ::= SEQUENCE {
   sl-RemoteUE-ToAddModList-r17 [0] SEQUENCE (SIZE (1..maxNrofRemoteUE-r17)) OF 
      SL-RemoteUE-ToAddMod-r17 OPTIONAL, -- Need N
   sl-RemoteUE-ToReleaseList-r17 [1] SEQUENCE (SIZE (1..maxNrofRemoteUE-r17)) OF 
      SL-DestinationIdentity-r16 OPTIONAL,
   ...
}

PagingUE-Identity ::= CHOICE {
   ng-5G-S-TMSI [0] NG-5G-S-TMSI,
   fullI-RNTI [1] I-RNTI-Value,
   ...
}

PagingRecord ::= SEQUENCE {
   ue-Identity [0] EXPLICIT PagingUE-Identity,
   accessType [1] ENUMERATED { non3GPP(0) } OPTIONAL,
   ...
}

PagingRecordList ::= SEQUENCE (SIZE (1..maxNrofPageRec)) OF PagingRecord

PagingRecord-v1700 ::= SEQUENCE {
   pagingCause-r17 [0] ENUMERATED { voice(0) } OPTIONAL -- Need N
}

PagingRecordList-v1700 ::= SEQUENCE (SIZE (1..maxNrofPageRec)) OF PagingRecord-v1700

PagingGroupList-r17 ::= SEQUENCE (SIZE (1..maxNrofPageGroup-r17)) OF TMGI-r17

Paging-v1700-IEs ::= SEQUENCE {
   pagingRecordList-v1700 [0] PagingRecordList-v1700 OPTIONAL, -- Need N
   pagingGroupList-r17 [1] PagingGroupList-r17 OPTIONAL, -- Need N
   nonCriticalExtension [2] SEQUENCE {

   } OPTIONAL
}

-- TAG-MOBILITYFROMNRCOMMAND-STOP
-- TAG-PAGING-START
Paging ::= SEQUENCE {
   pagingRecordList [0] PagingRecordList OPTIONAL, -- Need N
   lateNonCriticalExtension [1] OCTET STRING OPTIONAL,
   nonCriticalExtension [2] Paging-v1700-IEs OPTIONAL
}

-- TAG-NeedForGapNCSG-ConfigEUTRA-STOP
-- TAG-NEEDFORGAPNCSG-CONFIGNR-START
NeedForGapNCSG-ConfigNR-r17 ::= SEQUENCE {
   requestedTargetBandFilterNCSG-NR-r17 [0] SEQUENCE (SIZE (1..maxBands)) OF 
      FreqBandIndicatorNR OPTIONAL -- Need R
}

-- TAG-NeedForGapsInfoNR-STOP
-- TAG-NeedForGapNCSG-ConfigEUTRA-START
NeedForGapNCSG-ConfigEUTRA-r17 ::= SEQUENCE {
   requestedTargetBandFilterNCSG-EUTRA-r17 [0] SEQUENCE (SIZE (1..maxBandsEUTRA)) OF 
      FreqBandIndicatorEUTRA OPTIONAL -- Need R
}

MUSIM-Starting-SFN-AndSubframe-r17 ::= SEQUENCE {
   starting-SFN-r17 [0] INTEGER (0..1023),
   startingSubframe-r17 [1] INTEGER (0..9)
}

-- TAG-MUSIM-GAPID-STOP
-- TAG-MUSIM-GAPINFO-START
MUSIM-GapInfo-r17 ::= SEQUENCE {
   musim-Starting-SFN-AndSubframe-r17 [0] MUSIM-Starting-SFN-AndSubframe-r17
       OPTIONAL, -- Cond aperiodic
   musim-GapLength-r17 [1] ENUMERATED { ms3(0), ms4(1), ms6(2), ms10(3), 
      ms20(4) } OPTIONAL, -- Cond gapSetup
   musim-GapRepetitionAndOffset-r17 [2] EXPLICIT CHOICE {
      ms20-r17 [0] INTEGER (0..19),
      ms40-r17 [1] INTEGER (0..39),
      ms80-r17 [2] INTEGER (0..79),
      ms160-r17 [3] INTEGER (0..159),
      ms320-r17 [4] INTEGER (0..319),
      ms640-r17 [5] INTEGER (0..639),
      ms1280-r17 [6] INTEGER (0..1279),
      ms2560-r17 [7] INTEGER (0..2559),
      ms5120-r17 [8] INTEGER (0..5119),
      ...
   } OPTIONAL -- Cond periodic
}

MUSIM-Gap-r17 ::= SEQUENCE {
   musim-GapId-r17 [0] MUSIM-GapId-r17,
   musim-GapInfo-r17 [1] MUSIM-GapInfo-r17
}

-- TAG-MULTIFREQUENCYBANDLISTNR-SIB-STOP
-- TAG-MUSIM-GAPCONFIG-START
MUSIM-GapConfig-r17 ::= SEQUENCE {
   musim-GapToReleaseList-r17 [0] SEQUENCE (SIZE (1..3)) OF MUSIM-GapId-r17
       OPTIONAL, -- Need N
   musim-GapToAddModList-r17 [1] SEQUENCE (SIZE (1..3)) OF MUSIM-Gap-r17 OPTIONAL
      , -- Need N
   musim-AperiodicGap-r17 [2] MUSIM-GapInfo-r17 OPTIONAL,
   ...
}

-- TAG-ULEXCESSDELAYCONFIG-STOP
-- TAG-UL-GAPFR2-CONFIG-START
UL-GapFR2-Config-r17 ::= SEQUENCE {
   gapOffset-r17 [0] INTEGER (0..159),
   ugl-r17 [1] ENUMERATED { ms0dot125(0), ms0dot25(1), ms0dot5(2), ms1(3) },
   ugrp-r17 [2] ENUMERATED { ms5(0), ms20(1), ms40(2), ms160(3) },
   refFR2-ServCellAsyncCA-r17 [3] ServCellIndex OPTIONAL -- Cond AsyncCA
}

RAN-VisibleParameters-r17 ::= SEQUENCE {
   ran-VisiblePeriodicity-r17 [0] ENUMERATED { ms120(0), ms240(1), ms480(2), 
      ms640(3), ms1024(4) } OPTIONAL, -- Need S
   numberOfBufferLevelEntries-r17 [1] INTEGER (1..8) OPTIONAL, -- Need R
   reportPlayoutDelayForMediaStartup-r17 [2] BOOLEAN OPTIONAL,
   ...
}

MeasConfigAppLayer-r17 ::= SEQUENCE {
   measConfigAppLayerId-r17 [0] MeasConfigAppLayerId-r17,
   measConfigAppLayerContainer-r17 [1] OCTET STRING (SIZE (1..8000)) OPTIONAL, -- Need N
   serviceType-r17 [2] ENUMERATED { streaming(0), mtsi(1), vr(2), spare5(3), 
      spare4(4), spare3(5), spare2(6), spare1(7) } OPTIONAL, -- Need M
   pauseReporting-r17 [3] BOOLEAN OPTIONAL, -- Need M
   transmissionOfSessionStartStop-r17 [4] BOOLEAN OPTIONAL, -- Need M
   ran-VisibleParameters-r17 [5] EXPLICIT CHOICE {
      release [0] NULL,
      setup [1] EXPLICIT RAN-VisibleParameters-r17
   } OPTIONAL,
   ...
}

-- TAG-ABSOLUTETIMEINFO-STOP
-- TAG-APPLAYERMEASCONFIG-START
AppLayerMeasConfig-r17 ::= SEQUENCE {
   measConfigAppLayerToAddModList-r17 [0] SEQUENCE (SIZE (1..maxNrofAppLayerMeas-r17)) OF 
      MeasConfigAppLayer-r17 OPTIONAL, -- Need N
   measConfigAppLayerToReleaseList-r17 [1] SEQUENCE (SIZE (1..maxNrofAppLayerMeas-r17)) OF 
      MeasConfigAppLayerId-r17 OPTIONAL, -- Need N
   rrc-SegAllowed-r17 [2] ENUMERATED { enabled(0) } OPTIONAL,
   ...
}

UE-TxTEG-RequestUL-TDOA-Config-r17 ::= CHOICE {
   oneShot-r17 [0] NULL,
   periodicReporting-r17 [1] ENUMERATED { ms160(0), ms320(1), ms1280(2), 
      ms2560(3), ms61440(4), ms81920(5), ms368640(6), ms737280(7) }
}

RRCReconfiguration-v1700-IEs ::= SEQUENCE {
   otherConfig-v1700 [0] OtherConfig-v1700 OPTIONAL, -- Need M
   sl-L2RelayUE-Config-r17 [1] EXPLICIT CHOICE {
      release [0] NULL,
      setup [1] EXPLICIT SL-L2RelayUE-Config-r17
   } OPTIONAL, -- Need M
   sl-L2RemoteUE-Config-r17 [2] EXPLICIT CHOICE {
      release [0] NULL,
      setup [1] EXPLICIT SL-L2RemoteUE-Config-r17
   } OPTIONAL, -- Need M
   dedicatedPagingDelivery-r17 [3] OCTET STRING (CONTAINING Paging) OPTIONAL, -- Cond PagingRelay
   needForGapNCSG-ConfigNR-r17 [4] EXPLICIT CHOICE {
      release [0] NULL,
      setup [1] EXPLICIT NeedForGapNCSG-ConfigNR-r17
   } OPTIONAL, -- Need M
   needForGapNCSG-ConfigEUTRA-r17 [5] EXPLICIT CHOICE {
      release [0] NULL,
      setup [1] EXPLICIT NeedForGapNCSG-ConfigEUTRA-r17
   } OPTIONAL, -- Need M
   musim-GapConfig-r17 [6] EXPLICIT CHOICE {
      release [0] NULL,
      setup [1] EXPLICIT MUSIM-GapConfig-r17
   } OPTIONAL, -- Need M
   ul-GapFR2-Config-r17 [7] EXPLICIT CHOICE {
      release [0] NULL,
      setup [1] EXPLICIT UL-GapFR2-Config-r17
   } OPTIONAL, -- Need M
   scg-State-r17 [8] ENUMERATED { deactivated(0) } OPTIONAL, -- Need N
   appLayerMeasConfig-r17 [9] AppLayerMeasConfig-r17 OPTIONAL, -- Need M
   ue-TxTEG-RequestUL-TDOA-Config-r17 [10] EXPLICIT CHOICE {
      release [0] NULL,
      setup [1] EXPLICIT UE-TxTEG-RequestUL-TDOA-Config-r17
   } OPTIONAL, -- Need M
   nonCriticalExtension [11] SEQUENCE {

   } OPTIONAL
}

RRCReconfiguration-v1610-IEs ::= SEQUENCE {
   otherConfig-v1610 [0] OtherConfig-v1610 OPTIONAL, -- Need M
   bap-Config-r16 [1] EXPLICIT CHOICE {
      release [0] NULL,
      setup [1] EXPLICIT BAP-Config-r16
   } OPTIONAL, -- Need M
   iab-IP-AddressConfigurationList-r16 [2] IAB-IP-AddressConfigurationList-r16
       OPTIONAL, -- Need M
   conditionalReconfiguration-r16 [3] ConditionalReconfiguration-r16 OPTIONAL, -- Need M
   daps-SourceRelease-r16 [4] ENUMERATED { true(0) } OPTIONAL, -- Need N
   t316-r16 [5] EXPLICIT CHOICE {
      release [0] NULL,
      setup [1] EXPLICIT T316-r16
   } OPTIONAL, -- Need M
   needForGapsConfigNR-r16 [6] EXPLICIT CHOICE {
      release [0] NULL,
      setup [1] EXPLICIT NeedForGapsConfigNR-r16
   } OPTIONAL, -- Need M
   onDemandSIB-Request-r16 [7] EXPLICIT CHOICE {
      release [0] NULL,
      setup [1] EXPLICIT OnDemandSIB-Request-r16
   } OPTIONAL, -- Need M
   dedicatedPosSysInfoDelivery-r16 [8] OCTET STRING (CONTAINING 
      PosSystemInformation-r16-IEs) OPTIONAL, -- Need N
   sl-ConfigDedicatedNR-r16 [9] EXPLICIT CHOICE {
      release [0] NULL,
      setup [1] EXPLICIT SL-ConfigDedicatedNR-r16
   } OPTIONAL, -- Need M
   sl-ConfigDedicatedEUTRA-Info-r16 [10] EXPLICIT CHOICE {
      release [0] NULL,
      setup [1] EXPLICIT SL-ConfigDedicatedEUTRA-Info-r16
   } OPTIONAL, -- Need M
   targetCellSMTC-SCG-r16 [11] SSB-MTC OPTIONAL, -- Need S
   nonCriticalExtension [12] RRCReconfiguration-v1700-IEs OPTIONAL
}

RRCReconfiguration-v1560-IEs ::= SEQUENCE {
   mrdc-SecondaryCellGroupConfig [0] EXPLICIT CHOICE {
      release [0] NULL,
      setup [1] EXPLICIT MRDC-SecondaryCellGroupConfig
   } OPTIONAL, -- Need M
   radioBearerConfig2 [1] OCTET STRING (CONTAINING RadioBearerConfig) OPTIONAL,
       -- Need M
   sk-Counter [2] SK-Counter OPTIONAL, -- Need N
   nonCriticalExtension [3] RRCReconfiguration-v1610-IEs OPTIONAL
}

RRCReconfiguration-v1540-IEs ::= SEQUENCE {
   otherConfig-v1540 [0] OtherConfig-v1540 OPTIONAL, -- Need M
   nonCriticalExtension [1] RRCReconfiguration-v1560-IEs OPTIONAL
}

RRCReconfiguration-v1530-IEs ::= SEQUENCE {
   masterCellGroup [0] OCTET STRING (CONTAINING CellGroupConfig) OPTIONAL, -- Need M
   fullConfig [1] ENUMERATED { true(0) } OPTIONAL, -- Cond FullConfig
   dedicatedNAS-MessageList [2] SEQUENCE (SIZE (1..maxDRB)) OF DedicatedNAS-Message
       OPTIONAL, -- Cond nonHO
   masterKeyUpdate [3] MasterKeyUpdate OPTIONAL, -- Cond MasterKeyChange
   dedicatedSIB1-Delivery [4] OCTET STRING (CONTAINING SIB1) OPTIONAL, -- Need N
   dedicatedSystemInformationDelivery [5] OCTET STRING (CONTAINING 
      SystemInformation) OPTIONAL, -- Need N
   otherConfig [6] OtherConfig OPTIONAL, -- Need M
   nonCriticalExtension [7] RRCReconfiguration-v1540-IEs OPTIONAL
}

RRCReconfiguration-IEs ::= SEQUENCE {
   radioBearerConfig [0] RadioBearerConfig OPTIONAL, -- Need M
   secondaryCellGroup [1] OCTET STRING (CONTAINING CellGroupConfig) OPTIONAL, -- Cond SCG
   measConfig [2] MeasConfig OPTIONAL, -- Need M
   lateNonCriticalExtension [3] OCTET STRING OPTIONAL,
   nonCriticalExtension [4] RRCReconfiguration-v1530-IEs OPTIONAL
}

-- TAG-RRCREESTABLISHMENTREQUEST-STOP
-- TAG-RRCRECONFIGURATION-START
RRCReconfiguration ::= SEQUENCE {
   rrc-TransactionIdentifier [0] RRC-TransactionIdentifier,
   criticalExtensions [1] EXPLICIT CHOICE {
      rrcReconfiguration [0] RRCReconfiguration-IEs,
      criticalExtensionsFuture [1] SEQUENCE {

      }
   }
}

RRCResume-v1700-IEs ::= SEQUENCE {
   sl-ConfigDedicatedNR-r17 [0] EXPLICIT CHOICE {
      release [0] NULL,
      setup [1] EXPLICIT SL-ConfigDedicatedNR-r16
   } OPTIONAL, -- Cond L2RemoteUE
   sl-L2RemoteUE-Config-r17 [1] EXPLICIT CHOICE {
      release [0] NULL,
      setup [1] EXPLICIT SL-L2RemoteUE-Config-r17
   } OPTIONAL, -- Cond L2RemoteUE
   needForGapNCSG-ConfigNR-r17 [2] EXPLICIT CHOICE {
      release [0] NULL,
      setup [1] EXPLICIT NeedForGapNCSG-ConfigNR-r17
   } OPTIONAL, -- Need M
   needForGapNCSG-ConfigEUTRA-r17 [3] EXPLICIT CHOICE {
      release [0] NULL,
      setup [1] EXPLICIT NeedForGapNCSG-ConfigEUTRA-r17
   } OPTIONAL, -- Need M
   scg-State-r17 [4] ENUMERATED { deactivated(0) } OPTIONAL, -- Need N
   appLayerMeasConfig-r17 [5] AppLayerMeasConfig-r17 OPTIONAL, -- Need M
   nonCriticalExtension [6] SEQUENCE {

   } OPTIONAL
}

RRCResume-v1610-IEs ::= SEQUENCE {
   idleModeMeasurementReq-r16 [0] ENUMERATED { true(0) } OPTIONAL, -- Need N
   restoreMCG-SCells-r16 [1] ENUMERATED { true(0) } OPTIONAL, -- Need N
   restoreSCG-r16 [2] ENUMERATED { true(0) } OPTIONAL, -- Need N
   mrdc-SecondaryCellGroup-r16 [3] EXPLICIT CHOICE {
      nr-SCG-r16 [0] OCTET STRING (CONTAINING RRCReconfiguration),
      eutra-SCG-r16 [1] OCTET STRING
   } OPTIONAL, -- Cond RestoreSCG
   needForGapsConfigNR-r16 [4] EXPLICIT CHOICE {
      release [0] NULL,
      setup [1] EXPLICIT NeedForGapsConfigNR-r16
   } OPTIONAL, -- Need M
   nonCriticalExtension [5] RRCResume-v1700-IEs OPTIONAL
}

RRCResume-v1560-IEs ::= SEQUENCE {
   radioBearerConfig2 [0] OCTET STRING (CONTAINING RadioBearerConfig) OPTIONAL,
       -- Need M
   sk-Counter [1] SK-Counter OPTIONAL, -- Need N
   nonCriticalExtension [2] RRCResume-v1610-IEs OPTIONAL
}

RRCResume-IEs ::= SEQUENCE {
   radioBearerConfig [0] RadioBearerConfig OPTIONAL, -- Need M
   masterCellGroup [1] OCTET STRING (CONTAINING CellGroupConfig) OPTIONAL, -- Need M
   measConfig [2] MeasConfig OPTIONAL, -- Need M
   fullConfig [3] ENUMERATED { true(0) } OPTIONAL, -- Need N
   lateNonCriticalExtension [4] OCTET STRING OPTIONAL,
   nonCriticalExtension [5] RRCResume-v1560-IEs OPTIONAL
}

-- TAG-RRCRELEASE-STOP
-- TAG-RRCRESUME-START
RRCResume ::= SEQUENCE {
   rrc-TransactionIdentifier [0] RRC-TransactionIdentifier,
   criticalExtensions [1] EXPLICIT CHOICE {
      rrcResume [0] RRCResume-IEs,
      criticalExtensionsFuture [1] SEQUENCE {

      }
   }
}

CarrierInfoNR ::= SEQUENCE {
   carrierFreq [0] ARFCN-ValueNR,
   ssbSubcarrierSpacing [1] SubcarrierSpacing,
   smtc [2] SSB-MTC OPTIONAL,
   ...
}

RedirectedCarrierInfo-EUTRA ::= SEQUENCE {
   eutraFrequency [0] ARFCN-ValueEUTRA,
   cnType [1] ENUMERATED { epc(0), fiveGC(1) } OPTIONAL -- Need N
}

RedirectedCarrierInfo ::= CHOICE {
   nr [0] CarrierInfoNR,
   eutra [1] RedirectedCarrierInfo-EUTRA,
   ...
}

FreqPriorityEUTRA ::= SEQUENCE {
   carrierFreq [0] ARFCN-ValueEUTRA,
   cellReselectionPriority [1] CellReselectionPriority,
   cellReselectionSubPriority [2] CellReselectionSubPriority OPTIONAL -- Need R
}

FreqPriorityListEUTRA ::= SEQUENCE (SIZE (1..maxFreq)) OF FreqPriorityEUTRA

FreqPriorityNR ::= SEQUENCE {
   carrierFreq [0] ARFCN-ValueNR,
   cellReselectionPriority [1] CellReselectionPriority,
   cellReselectionSubPriority [2] CellReselectionSubPriority OPTIONAL -- Need R
}

FreqPriorityListNR ::= SEQUENCE (SIZE (1..maxFreq)) OF FreqPriorityNR

SliceInfoDedicated-r17 ::= SEQUENCE {
   nsag-IdentityInfo-r17 [0] NSAG-IdentityInfo-r17,
   nsag-CellReselectionPriority-r17 [1] CellReselectionPriority OPTIONAL, -- Need R
   nsag-CellReselectionSubPriority-r17 [2] CellReselectionSubPriority OPTIONAL -- Need R
}

SliceInfoListDedicated-r17 ::= SEQUENCE (SIZE (1..maxSliceInfo-r17)) OF SliceInfoDedicated-r17

FreqPriorityDedicatedSlicing-r17 ::= SEQUENCE {
   dl-ExplicitCarrierFreq-r17 [0] ARFCN-ValueNR,
   sliceInfoListDedicated-r17 [1] SliceInfoListDedicated-r17 OPTIONAL -- Cond Mandatory
}

-- TAG-FREQBANDINDICATORNR-STOP
-- TAG-FREQPRIORITYLISTDEDICATEDSLICING-START
FreqPriorityListDedicatedSlicing-r17 ::= SEQUENCE (SIZE (1..maxFreq)) OF 
   FreqPriorityDedicatedSlicing-r17

CellReselectionPriorities ::= SEQUENCE {
   freqPriorityListEUTRA [0] FreqPriorityListEUTRA OPTIONAL, -- Need M
   freqPriorityListNR [1] FreqPriorityListNR OPTIONAL, -- Need M
   t320 [2] ENUMERATED { min5(0), min10(1), min20(2), min30(3), min60(4), 
      min120(5), min180(6), spare1(7) } OPTIONAL,
   ...,
   [[
      freqPriorityListDedicatedSlicing-r17 [3] 
         FreqPriorityListDedicatedSlicing-r17 OPTIONAL
   ]]
}

PLMN-RAN-AreaCell ::= SEQUENCE {
   plmn-Identity [0] PLMN-Identity OPTIONAL, -- Need S
   ran-AreaCells [1] SEQUENCE (SIZE (1..32)) OF CellIdentity
}

PLMN-RAN-AreaCellList ::= SEQUENCE (SIZE (1..maxPLMNIdentities)) OF PLMN-RAN-AreaCell

RAN-AreaConfig ::= SEQUENCE {
   trackingAreaCode [0] TrackingAreaCode,
   ran-AreaCodeList [1] SEQUENCE (SIZE (1..32)) OF RAN-AreaCode OPTIONAL -- Need R
}

PLMN-RAN-AreaConfig ::= SEQUENCE {
   plmn-Identity [0] PLMN-Identity OPTIONAL, -- Need S
   ran-Area [1] SEQUENCE (SIZE (1..16)) OF RAN-AreaConfig
}

PLMN-RAN-AreaConfigList ::= SEQUENCE (SIZE (1..maxPLMNIdentities)) OF PLMN-RAN-AreaConfig

RAN-NotificationAreaInfo ::= CHOICE {
   cellList [0] PLMN-RAN-AreaCellList,
   ran-AreaConfigList [1] PLMN-RAN-AreaConfigList,
   ...
}

SDT-Config-r17 ::= SEQUENCE {
   sdt-DRB-List-r17 [0] SEQUENCE (SIZE (0..maxDRB)) OF DRB-Identity OPTIONAL, -- Need M
   sdt-SRB2-Indication-r17 [1] ENUMERATED { allowed(0) } OPTIONAL, -- Need R
   sdt-MAC-PHY-CG-Config-r17 [2] EXPLICIT CHOICE {
      release [0] NULL,
      setup [1] EXPLICIT SDT-CG-Config-r17
   } OPTIONAL, -- Need M
   sdt-DRB-ContinueROHC-r17 [3] ENUMERATED { cell(0), rna(1) } OPTIONAL -- Need S
}

SuspendConfig ::= SEQUENCE {
   fullI-RNTI [0] I-RNTI-Value,
   shortI-RNTI [1] ShortI-RNTI-Value,
   ran-PagingCycle [2] PagingCycle,
   ran-NotificationAreaInfo [3] EXPLICIT RAN-NotificationAreaInfo OPTIONAL, -- Need M
   t380 [4] PeriodicRNAU-TimerValue OPTIONAL, -- Need R
   nextHopChainingCount [5] NextHopChainingCount,
   ...,
   [[
      sl-UEIdentityRemote-r17 [6] RNTI-Value OPTIONAL,
      sdt-Config-r17 [7] EXPLICIT CHOICE {
         release [0] NULL,
         setup [1] EXPLICIT SDT-Config-r17
      } OPTIONAL,
      srs-PosRRC-Inactive-r17 [8] EXPLICIT CHOICE {
         release [0] NULL,
         setup [1] EXPLICIT SRS-PosRRC-Inactive-r17
      } OPTIONAL,
      ran-ExtendedPagingCycle-r17 [9] ExtendedPagingCycle-r17 OPTIONAL
   ]],
   [[
      ncd-SSB-RedCapInitialBWP-SDT-r17 [10] EXPLICIT CHOICE {
         release [0] NULL,
         setup [1] EXPLICIT NonCellDefiningSSB-r17
      } OPTIONAL
   ]]
}

ValidityCellList ::= SEQUENCE (SIZE (1..maxCellMeasIdle-r16)) OF PCI-Range

ValidityArea-r16 ::= SEQUENCE {
   carrierFreq-r16 [0] ARFCN-ValueNR,
   validityCellList-r16 [1] ValidityCellList OPTIONAL -- Need N
}

ValidityAreaList-r16 ::= SEQUENCE (SIZE (1..maxFreqIdle-r16)) OF ValidityArea-r16

MeasIdleConfigDedicated-r16 ::= SEQUENCE {
   measIdleCarrierListNR-r16 [0] SEQUENCE (SIZE (1..maxFreqIdle-r16)) OF MeasIdleCarrierNR-r16
       OPTIONAL, -- Need N
   measIdleCarrierListEUTRA-r16 [1] SEQUENCE (SIZE (1..maxFreqIdle-r16)) OF 
      MeasIdleCarrierEUTRA-r16 OPTIONAL, -- Need N
   measIdleDuration-r16 [2] ENUMERATED { sec10(0), sec30(1), sec60(2), 
      sec120(3), sec180(4), sec240(5), sec300(6), spare(7) },
   validityAreaList-r16 [3] ValidityAreaList-r16 OPTIONAL,
   ...
}

RRCRelease-v1710-IEs ::= SEQUENCE {
   noLastCellUpdate-r17 [0] ENUMERATED { true(0) } OPTIONAL, -- Need S
   nonCriticalExtension [1] SEQUENCE {

   } OPTIONAL
}

RRCRelease-v1650-IEs ::= SEQUENCE {
   mpsPriorityIndication-r16 [0] ENUMERATED { true(0) } OPTIONAL, -- Cond Redirection2
   nonCriticalExtension [1] RRCRelease-v1710-IEs OPTIONAL
}

RRCRelease-v1610-IEs ::= SEQUENCE {
   voiceFallbackIndication-r16 [0] ENUMERATED { true(0) } OPTIONAL, -- Need N
   measIdleConfig-r16 [1] EXPLICIT CHOICE {
      release [0] NULL,
      setup [1] EXPLICIT MeasIdleConfigDedicated-r16
   } OPTIONAL, -- Need M
   nonCriticalExtension [2] RRCRelease-v1650-IEs OPTIONAL
}

RRCRelease-v1540-IEs ::= SEQUENCE {
   waitTime [0] RejectWaitTime OPTIONAL, -- Need N
   nonCriticalExtension [1] RRCRelease-v1610-IEs OPTIONAL
}

RRCRelease-IEs ::= SEQUENCE {
   redirectedCarrierInfo [0] EXPLICIT RedirectedCarrierInfo OPTIONAL, -- Need N
   cellReselectionPriorities [1] CellReselectionPriorities OPTIONAL, -- Need R
   suspendConfig [2] SuspendConfig OPTIONAL, -- Need R
   deprioritisationReq [3] SEQUENCE {
      deprioritisationType [0] ENUMERATED { frequency(0), nr(1) },
      deprioritisationTimer [1] ENUMERATED { min5(0), min10(1), min15(2), 
         min30(3) }
   } OPTIONAL, -- Need N
   lateNonCriticalExtension [4] OCTET STRING OPTIONAL,
   nonCriticalExtension [5] RRCRelease-v1540-IEs OPTIONAL
}

-- TAG-RRCREJECT-STOP
-- TAG-RRCRELEASE-START
RRCRelease ::= SEQUENCE {
   rrc-TransactionIdentifier [0] RRC-TransactionIdentifier,
   criticalExtensions [1] EXPLICIT CHOICE {
      rrcRelease [0] RRCRelease-IEs,
      criticalExtensionsFuture [1] SEQUENCE {

      }
   }
}

RRCReestablishment-v1700-IEs ::= SEQUENCE {
   sl-L2RemoteUE-Config-r17 [0] EXPLICIT CHOICE {
      release [0] NULL,
      setup [1] EXPLICIT SL-L2RemoteUE-Config-r17
   } OPTIONAL, -- Cond L2RemoteUE
   nonCriticalExtension [1] SEQUENCE {

   } OPTIONAL
}

RRCReestablishment-IEs ::= SEQUENCE {
   nextHopChainingCount [0] NextHopChainingCount,
   lateNonCriticalExtension [1] OCTET STRING OPTIONAL,
   nonCriticalExtension [2] RRCReestablishment-v1700-IEs OPTIONAL
}

-- TAG-PAGING-STOP
-- TAG-RRCREESTABLISHMENT-START
RRCReestablishment ::= SEQUENCE {
   rrc-TransactionIdentifier [0] RRC-TransactionIdentifier,
   criticalExtensions [1] EXPLICIT CHOICE {
      rrcReestablishment [0] RRCReestablishment-IEs,
      criticalExtensionsFuture [1] SEQUENCE {

      }
   }
}

SecurityConfigSMC ::= SEQUENCE {
   securityAlgorithmConfig [0] SecurityAlgorithmConfig,
   ...
}

SecurityModeCommand-IEs ::= SEQUENCE {
   securityConfigSMC [0] SecurityConfigSMC,
   lateNonCriticalExtension [1] OCTET STRING OPTIONAL,
   nonCriticalExtension [2] SEQUENCE {

   } OPTIONAL
}

-- TAG-SCGFAILUREINFORMATIONEUTRA-STOP
-- TAG-SECURITYMODECOMMAND-START
SecurityModeCommand ::= SEQUENCE {
   rrc-TransactionIdentifier [0] RRC-TransactionIdentifier,
   criticalExtensions [1] EXPLICIT CHOICE {
      securityModeCommand [0] SecurityModeCommand-IEs,
      criticalExtensionsFuture [1] SEQUENCE {

      }
   }
}

-- TAG-RSSI-RANGE-STOP
-- TAG-RXTXTIMEDIFF-START
RxTxTimeDiff-r17 ::= SEQUENCE {
   result-k5-r17 [0] INTEGER (0..61565) OPTIONAL,
   ...
}

DLInformationTransfer-v1700-IEs ::= SEQUENCE {
   dedicatedInfoF1c-r17 [0] DedicatedInfoF1c-r17 OPTIONAL, -- Need N
   rxTxTimeDiff-gNB-r17 [1] RxTxTimeDiff-r17 OPTIONAL, -- Need N
   ta-PDC-r17 [2] ENUMERATED { activate(0), deactivate(1) } OPTIONAL, -- Need N
   sib9Fallback-r17 [3] ENUMERATED { true(0) } OPTIONAL, -- Need N
   nonCriticalExtension [4] SEQUENCE {

   } OPTIONAL
}

DLInformationTransfer-v1610-IEs ::= SEQUENCE {
   referenceTimeInfo-r16 [0] ReferenceTimeInfo-r16 OPTIONAL, -- Need N
   nonCriticalExtension [1] DLInformationTransfer-v1700-IEs OPTIONAL
}

DLInformationTransfer-IEs ::= SEQUENCE {
   dedicatedNAS-Message [0] DedicatedNAS-Message OPTIONAL, -- Need N
   lateNonCriticalExtension [1] OCTET STRING OPTIONAL,
   nonCriticalExtension [2] DLInformationTransfer-v1610-IEs OPTIONAL
}

-- TAG-DLDEDICATEDMESSAGESEGMENT-STOP
-- TAG-DLINFORMATIONTRANSFER-START
DLInformationTransfer ::= SEQUENCE {
   rrc-TransactionIdentifier [0] RRC-TransactionIdentifier,
   criticalExtensions [1] EXPLICIT CHOICE {
      dlInformationTransfer [0] DLInformationTransfer-IEs,
      criticalExtensionsFuture [1] SEQUENCE {

      }
   }
}

UE-CapabilityRAT-Request ::= SEQUENCE {
   rat-Type [0] RAT-Type,
   capabilityRequestFilter [1] OCTET STRING OPTIONAL,
   ...
}

-- TAG-UE-CAPABILITYRAT-CONTAINERLIST-STOP
-- TAG-UE-CAPABILITYRAT-REQUESTLIST-START
UE-CapabilityRAT-RequestList ::= SEQUENCE (SIZE (1..maxRAT-CapabilityContainers)) OF 
   UE-CapabilityRAT-Request

CellGrouping-r16 ::= SEQUENCE {
   mcg-r16 [0] SEQUENCE (SIZE (1..maxBands)) OF FreqBandIndicatorNR,
   scg-r16 [1] SEQUENCE (SIZE (1..maxBands)) OF FreqBandIndicatorNR,
   mode-r16 [2] ENUMERATED { sync(0), async(1) }
}

-- TAG-UE-CAPABILITYRAT-REQUESTLIST-STOP
-- TAG-UE-CAPABILITYREQUESTFILTERCOMMON-START
UE-CapabilityRequestFilterCommon ::= SEQUENCE {
   mrdc-Request [0] SEQUENCE {
      omitEN-DC [0] ENUMERATED { true(0) } OPTIONAL, -- Need N
      includeNR-DC [1] ENUMERATED { true(0) } OPTIONAL, -- Need N
      includeNE-DC [2] ENUMERATED { true(0) } OPTIONAL -- Need N
   } OPTIONAL,
   ...,
   [[
      codebookTypeRequest-r16 [1] SEQUENCE {
         type1-SinglePanel-r16 [0] ENUMERATED { true(0) } OPTIONAL, -- Need N
         type1-MultiPanel-r16 [1] ENUMERATED { true(0) } OPTIONAL, -- Need N
         type2-r16 [2] ENUMERATED { true(0) } OPTIONAL, -- Need N
         type2-PortSelection-r16 [3] ENUMERATED { true(0) } OPTIONAL -- Need N
      } OPTIONAL,
      uplinkTxSwitchRequest-r16 [2] ENUMERATED { true(0) } OPTIONAL
   ]],
   [[
      requestedCellGrouping-r16 [3] SEQUENCE (SIZE (1..maxCellGroupings-r16)) OF CellGrouping-r16
          OPTIONAL
   ]],
   [[
      fallbackGroupFiveRequest-r17 [4] ENUMERATED { true(0) } OPTIONAL
   ]]
}

UECapabilityEnquiry-v1610-IEs ::= SEQUENCE {
   rrc-SegAllowed-r16 [0] ENUMERATED { enabled(0) } OPTIONAL, -- Need N
   nonCriticalExtension [1] SEQUENCE {

   } OPTIONAL
}

UECapabilityEnquiry-v1560-IEs ::= SEQUENCE {
   capabilityRequestFilterCommon [0] UE-CapabilityRequestFilterCommon OPTIONAL,
       -- Need N
   nonCriticalExtension [1] UECapabilityEnquiry-v1610-IEs OPTIONAL
}

UECapabilityEnquiry-IEs ::= SEQUENCE {
   ue-CapabilityRAT-RequestList [0] UE-CapabilityRAT-RequestList,
   lateNonCriticalExtension [1] OCTET STRING OPTIONAL,
   ue-CapabilityEnquiryExt [2] OCTET STRING (CONTAINING 
      UECapabilityEnquiry-v1560-IEs) OPTIONAL --  Need N
}

-- TAG-UEASSISTANCEINFORMATION-STOP
-- TAG-UECAPABILITYENQUIRY-START
UECapabilityEnquiry ::= SEQUENCE {
   rrc-TransactionIdentifier [0] RRC-TransactionIdentifier,
   criticalExtensions [1] EXPLICIT CHOICE {
      ueCapabilityEnquiry [0] UECapabilityEnquiry-IEs,
      criticalExtensionsFuture [1] SEQUENCE {

      }
   }
}

DRB-CountMSB-Info ::= SEQUENCE {
   drb-Identity [0] DRB-Identity,
   countMSB-Uplink [1] INTEGER (0..33554431),
   countMSB-Downlink [2] INTEGER (0..33554431)
}

DRB-CountMSB-InfoList ::= SEQUENCE (SIZE (1..maxDRB)) OF DRB-CountMSB-Info

CounterCheck-IEs ::= SEQUENCE {
   drb-CountMSB-InfoList [0] DRB-CountMSB-InfoList,
   lateNonCriticalExtension [1] OCTET STRING OPTIONAL,
   nonCriticalExtension [2] SEQUENCE {

   } OPTIONAL
}

-- TAG-UL-DCCH-MESSAGE-STOP
-- TAG-COUNTERCHECK-START
CounterCheck ::= SEQUENCE {
   rrc-TransactionIdentifier [0] RRC-TransactionIdentifier,
   criticalExtensions [1] EXPLICIT CHOICE {
      counterCheck [0] CounterCheck-IEs,
      criticalExtensionsFuture [1] SEQUENCE {

      }
   }
}

MobilityFromNRCommand-v1610-IEs ::= SEQUENCE {
   voiceFallbackIndication-r16 [0] ENUMERATED { true(0) } OPTIONAL, -- Need N
   nonCriticalExtension [1] SEQUENCE {

   } OPTIONAL
}

MobilityFromNRCommand-IEs ::= SEQUENCE {
   targetRAT-Type [0] ENUMERATED { eutra(0), utra-fdd-v1610(1), spare2(2), 
      spare1(3), ... },
   targetRAT-MessageContainer [1] OCTET STRING,
   nas-SecurityParamFromNR [2] OCTET STRING OPTIONAL, -- Cond HO-ToEPCUTRAN
   lateNonCriticalExtension [3] OCTET STRING OPTIONAL,
   nonCriticalExtension [4] MobilityFromNRCommand-v1610-IEs OPTIONAL
}

-- TAG-MIB-STOP
-- TAG-MOBILITYFROMNRCOMMAND-START
MobilityFromNRCommand ::= SEQUENCE {
   rrc-TransactionIdentifier [0] RRC-TransactionIdentifier,
   criticalExtensions [1] EXPLICIT CHOICE {
      mobilityFromNRCommand [0] MobilityFromNRCommand-IEs,
      criticalExtensionsFuture [1] SEQUENCE {

      }
   }
}

DLDedicatedMessageSegment-r16-IEs ::= SEQUENCE {
   segmentNumber-r16 [0] INTEGER (0..4),
   rrc-MessageSegmentContainer-r16 [1] OCTET STRING,
   rrc-MessageSegmentType-r16 [2] ENUMERATED { notLastSegment(0), 
      lastSegment(1) },
   lateNonCriticalExtension [3] OCTET STRING OPTIONAL,
   nonCriticalExtension [4] SEQUENCE {

   } OPTIONAL
}

-- TAG-DEDICATEDSIBREQUEST-STOP
-- TAG-DLDEDICATEDMESSAGESEGMENT-START
DLDedicatedMessageSegment-r16 ::= SEQUENCE {
   criticalExtensions [0] EXPLICIT CHOICE {
      dlDedicatedMessageSegment-r16 [0] DLDedicatedMessageSegment-r16-IEs,
      criticalExtensionsFuture [1] SEQUENCE {

      }
   }
}

UEInformationRequest-v1700-IEs ::= SEQUENCE {
   successHO-ReportReq-r17 [0] ENUMERATED { true(0) } OPTIONAL, -- Need N
   coarseLocationRequest-r17 [1] ENUMERATED { true(0) } OPTIONAL, -- Need N
   nonCriticalExtension [2] SEQUENCE {

   } OPTIONAL
}

UEInformationRequest-r16-IEs ::= SEQUENCE {
   idleModeMeasurementReq-r16 [0] ENUMERATED { true(0) } OPTIONAL, -- Need N
   logMeasReportReq-r16 [1] ENUMERATED { true(0) } OPTIONAL, -- Need N
   connEstFailReportReq-r16 [2] ENUMERATED { true(0) } OPTIONAL, -- Need N
   ra-ReportReq-r16 [3] ENUMERATED { true(0) } OPTIONAL, -- Need N
   rlf-ReportReq-r16 [4] ENUMERATED { true(0) } OPTIONAL, -- Need N
   mobilityHistoryReportReq-r16 [5] ENUMERATED { true(0) } OPTIONAL, -- Need N
   lateNonCriticalExtension [6] OCTET STRING OPTIONAL,
   nonCriticalExtension [7] UEInformationRequest-v1700-IEs OPTIONAL
}

-- TAG-UECAPABILITYINFORMATION-STOP
-- TAG-UEINFORMATIONREQUEST-START
UEInformationRequest-r16 ::= SEQUENCE {
   rrc-TransactionIdentifier [0] RRC-TransactionIdentifier,
   criticalExtensions [1] EXPLICIT CHOICE {
      ueInformationRequest-r16 [0] UEInformationRequest-r16-IEs,
      criticalExtensionsFuture [1] SEQUENCE {

      }
   }
}

DLInformationTransferMRDC-r16-IEs ::= SEQUENCE {
   dl-DCCH-MessageNR-r16 [0] OCTET STRING OPTIONAL, -- Need N
   dl-DCCH-MessageEUTRA-r16 [1] OCTET STRING OPTIONAL, -- Need N
   lateNonCriticalExtension [2] OCTET STRING OPTIONAL,
   nonCriticalExtension [3] SEQUENCE {

   } OPTIONAL
}

-- TAG-DLINFORMATIONTRANSFER-STOP
-- TAG-DLINFORMATIONTRANSFERMRDC-START
DLInformationTransferMRDC-r16 ::= SEQUENCE {
   criticalExtensions [0] EXPLICIT CHOICE {
      c1 [0] EXPLICIT CHOICE {
         dlInformationTransferMRDC-r16 [0] DLInformationTransferMRDC-r16-IEs,
         spare3 [1] NULL,
         spare2 [2] NULL,
         spare1 [3] NULL
      },
      criticalExtensionsFuture [1] SEQUENCE {

      }
   }
}

-- TAG-SENSORNAMELIST-STOP
-- TAG-TRACEREFERENCE-START
TraceReference-r16 ::= SEQUENCE {
   plmn-Identity-r16 [0] PLMN-Identity,
   traceId-r16 [1] OCTET STRING (SIZE (3))
}

CellGlobalIdList-r16 ::= SEQUENCE (SIZE (1..32)) OF CGI-Info-Logging-r16

TrackingAreaCodeList-r16 ::= SEQUENCE (SIZE (1..8)) OF TrackingAreaCode

TrackingAreaIdentity-r16 ::= SEQUENCE {
   plmn-Identity-r16 [0] PLMN-Identity,
   trackingAreaCode-r16 [1] TrackingAreaCode
}

TrackingAreaIdentityList-r16 ::= SEQUENCE (SIZE (1..8)) OF 
   TrackingAreaIdentity-r16

AreaConfig-r16 ::= CHOICE {
   cellGlobalIdList-r16 [0] CellGlobalIdList-r16,
   trackingAreaCodeList-r16 [1] TrackingAreaCodeList-r16,
   trackingAreaIdentityList-r16 [2] TrackingAreaIdentityList-r16
}

InterFreqTargetInfo-r16 ::= SEQUENCE {
   dl-CarrierFreq-r16 [0] ARFCN-ValueNR,
   cellList-r16 [1] SEQUENCE (SIZE (1..32)) OF PhysCellId OPTIONAL -- Need R
}

-- TAG-APPLAYERMEASCONFIG-STOP
-- TAG-AREACONFIGURATION-START
AreaConfiguration-r16 ::= SEQUENCE {
   areaConfig-r16 [0] EXPLICIT AreaConfig-r16,
   interFreqTargetList-r16 [1] SEQUENCE (SIZE (1..maxFreq)) OF InterFreqTargetInfo-r16
       OPTIONAL -- Need R
}

-- TAG-PLMN-IDENTITYINFOLIST-STOP
-- TAG-PLMNIDENTITYLIST2-START
PLMN-IdentityList2-r16 ::= SEQUENCE (SIZE (1..16)) OF PLMN-Identity

LoggedPeriodicalReportConfig-r16 ::= SEQUENCE {
   loggingInterval-r16 [0] LoggingInterval-r16,
   ...
}

EventType-r16 ::= CHOICE {
   outOfCoverage [0] NULL,
   eventL1 [1] SEQUENCE {
      l1-Threshold [0] EXPLICIT MeasTriggerQuantity,
      hysteresis [1] Hysteresis,
      timeToTrigger [2] TimeToTrigger
   },
   ...
}

LoggedEventTriggerConfig-r16 ::= SEQUENCE {
   eventType-r16 [0] EXPLICIT EventType-r16,
   loggingInterval-r16 [1] LoggingInterval-r16,
   ...
}

AreaConfiguration-r17 ::= SEQUENCE {
   areaConfig-r17 [0] EXPLICIT AreaConfig-r16 OPTIONAL, -- Need R
   interFreqTargetList-r17 [1] SEQUENCE (SIZE (1..maxFreq)) OF InterFreqTargetInfo-r16
       OPTIONAL -- Need R
}

LoggedMeasurementConfiguration-v1700-IEs ::= SEQUENCE {
   sigLoggedMeasType-r17 [0] ENUMERATED { true(0) } OPTIONAL, -- Need R
   earlyMeasIndication-r17 [1] ENUMERATED { true(0) } OPTIONAL, -- Need R
   areaConfiguration-r17 [2] AreaConfiguration-r17 OPTIONAL, --Need R
   nonCriticalExtension [3] SEQUENCE {

   } OPTIONAL
}

LoggedMeasurementConfiguration-r16-IEs ::= SEQUENCE {
   traceReference-r16 [0] TraceReference-r16,
   traceRecordingSessionRef-r16 [1] OCTET STRING (SIZE (2)),
   tce-Id-r16 [2] OCTET STRING (SIZE (1)),
   absoluteTimeInfo-r16 [3] AbsoluteTimeInfo-r16,
   areaConfiguration-r16 [4] AreaConfiguration-r16 OPTIONAL, --Need R
   plmn-IdentityList-r16 [5] PLMN-IdentityList2-r16 OPTIONAL, --Need R
   bt-NameList-r16 [6] EXPLICIT CHOICE {
      release [0] NULL,
      setup [1] EXPLICIT BT-NameList-r16
   } OPTIONAL, --Need M
   wlan-NameList-r16 [7] EXPLICIT CHOICE {
      release [0] NULL,
      setup [1] EXPLICIT WLAN-NameList-r16
   } OPTIONAL, --Need M
   sensor-NameList-r16 [8] EXPLICIT CHOICE {
      release [0] NULL,
      setup [1] EXPLICIT Sensor-NameList-r16
   } OPTIONAL, --Need M
   loggingDuration-r16 [9] LoggingDuration-r16,
   reportType [10] EXPLICIT CHOICE {
      periodical [0] LoggedPeriodicalReportConfig-r16,
      eventTriggered [1] LoggedEventTriggerConfig-r16,
      ...
   },
   lateNonCriticalExtension [11] OCTET STRING OPTIONAL,
   nonCriticalExtension [12] LoggedMeasurementConfiguration-v1700-IEs OPTIONAL
}

-- TAG-LOCATIONMEASUREMENTINDICATION-STOP
-- TAG-LOGGEDMEASUREMENTCONFIGURATION-START
LoggedMeasurementConfiguration-r16 ::= SEQUENCE {
   criticalExtensions [0] EXPLICIT CHOICE {
      loggedMeasurementConfiguration-r16 [0] 
         LoggedMeasurementConfiguration-r16-IEs,
      criticalExtensionsFuture [1] SEQUENCE {

      }
   }
}

DL-DCCH-MessageType ::= CHOICE {
   c1 [0] EXPLICIT CHOICE {
      rrcReconfiguration [0] RRCReconfiguration,
      rrcResume [1] RRCResume,
      rrcRelease [2] RRCRelease,
      rrcReestablishment [3] RRCReestablishment,
      securityModeCommand [4] SecurityModeCommand,
      dlInformationTransfer [5] DLInformationTransfer,
      ueCapabilityEnquiry [6] UECapabilityEnquiry,
      counterCheck [7] CounterCheck,
      mobilityFromNRCommand [8] MobilityFromNRCommand,
      dlDedicatedMessageSegment-r16 [9] DLDedicatedMessageSegment-r16,
      ueInformationRequest-r16 [10] UEInformationRequest-r16,
      dlInformationTransferMRDC-r16 [11] DLInformationTransferMRDC-r16,
      loggedMeasurementConfiguration-r16 [12] 
         LoggedMeasurementConfiguration-r16,
      spare3 [13] NULL,
      spare2 [14] NULL,
      spare1 [15] NULL
   },
   messageClassExtension [1] SEQUENCE {

   }
}

-- TAG-DL-CCCH-MESSAGE-STOP
-- TAG-DL-DCCH-MESSAGE-START
DL-DCCH-Message ::= SEQUENCE {
   message [0] EXPLICIT DL-DCCH-MessageType
}

MRB-PDCP-ConfigBroadcast-r17 ::= SEQUENCE {
   pdcp-SN-SizeDL-r17 [0] ENUMERATED { len12bits(0) } OPTIONAL, -- Need S
   headerCompression-r17 [1] EXPLICIT CHOICE {
      notUsed [0] NULL,
      rohc [1] SEQUENCE {
         maxCID-r17 [0] INTEGER (1..16) DEFAULT 15,
         profiles-r17 [1] SEQUENCE {
            profile0x0000-r17 [0] BOOLEAN,
            profile0x0001-r17 [1] BOOLEAN,
            profile0x0002-r17 [2] BOOLEAN
         }
      }
   },
   t-Reordering-r17 [2] ENUMERATED { ms1(0), ms10(1), ms40(2), ms160(3), 
      ms500(4), ms1000(5), ms1250(6), ms2750(7) } OPTIONAL -- Need S
}

MRB-RLC-ConfigBroadcast-r17 ::= SEQUENCE {
   logicalChannelIdentity-r17 [0] LogicalChannelIdentity,
   sn-FieldLength-r17 [1] ENUMERATED { size6(0) } OPTIONAL, -- Need S
   t-Reassembly-r17 [2] T-Reassembly OPTIONAL -- Need S
}

MRB-InfoBroadcast-r17 ::= SEQUENCE {
   pdcp-Config-r17 [0] MRB-PDCP-ConfigBroadcast-r17,
   rlc-Config-r17 [1] MRB-RLC-ConfigBroadcast-r17,
   ...
}

MRB-ListBroadcast-r17 ::= SEQUENCE (SIZE (1..maxNrofMRB-Broadcast-r17)) OF MRB-InfoBroadcast-r17

MBS-SessionInfo-r17 ::= SEQUENCE {
   mbs-SessionId-r17 [0] TMGI-r17,
   g-RNTI-r17 [1] RNTI-Value,
   mrb-ListBroadcast-r17 [2] MRB-ListBroadcast-r17,
   mtch-SchedulingInfo-r17 [3] DRX-ConfigPTM-Index-r17 OPTIONAL, -- Need S
   mtch-NeighbourCell-r17 [4] BIT STRING  (SIZE (maxNeighCellMBS-r17)) OPTIONAL, -- Need S
   pdsch-ConfigIndex-r17 [5] PDSCH-ConfigIndex-r17 OPTIONAL, -- Need S
   mtch-SSB-MappingWindowIndex-r17 [6] MTCH-SSB-MappingWindowIndex-r17 OPTIONAL
       -- Cond MTCH-Mapping
}

-- TAG-MBS-SERVICELIST-STOP
-- TAG-MBS-SESSIONINFOLIST-START
MBS-SessionInfoList-r17 ::= SEQUENCE (SIZE (1..maxNrofMBS-Session-r17)) OF MBS-SessionInfo-r17

MBS-NeighbourCell-r17 ::= SEQUENCE {
   physCellId-r17 [0] PhysCellId,
   carrierFreq-r17 [1] ARFCN-ValueNR OPTIONAL -- Need S
}

-- TAG-DRX-CONFIGPTM-STOP
-- TAG-MBS-NEIGHBOURCELLLIST-START
MBS-NeighbourCellList-r17 ::= SEQUENCE (SIZE (0..maxNeighCellMBS-r17)) OF MBS-NeighbourCell-r17

MTCH-SSB-MappingWindowCycleOffset-r17 ::= CHOICE {
   ms10 [0] INTEGER (0..9),
   ms20 [1] INTEGER (0..19),
   ms32 [2] INTEGER (0..31),
   ms64 [3] INTEGER (0..63),
   ms128 [4] INTEGER (0..127),
   ms256 [5] INTEGER (0..255)
}

-- TAG-MBS-SESSIONINFOLIST-STOP
-- TAG-MTCH-SSB-MAPPINGWINDOWLIST-START
MTCH-SSB-MappingWindowList-r17 ::= SEQUENCE (SIZE (1..maxNrofMTCH-SSB-MappingWindow-r17)) OF 
   MTCH-SSB-MappingWindowCycleOffset-r17

MBSBroadcastConfiguration-r17-IEs ::= SEQUENCE {
   mbs-SessionInfoList-r17 [0] MBS-SessionInfoList-r17 OPTIONAL, -- Need R
   mbs-NeighbourCellList-r17 [1] MBS-NeighbourCellList-r17 OPTIONAL, -- Need S
   drx-ConfigPTM-List-r17 [2] SEQUENCE (SIZE (1..maxNrofDRX-ConfigPTM-r17)) OF DRX-ConfigPTM-r17
       OPTIONAL, -- Need R
   pdsch-ConfigMTCH-r17 [3] PDSCH-ConfigBroadcast-r17 OPTIONAL, -- Need S
   mtch-SSB-MappingWindowList-r17 [4] MTCH-SSB-MappingWindowList-r17 OPTIONAL, -- Need R
   lateNonCriticalExtension [5] OCTET STRING OPTIONAL,
   nonCriticalExtension [6] SEQUENCE {

   } OPTIONAL
}

-- TAG-LOGGEDMEASUREMENTCONFIGURATION-STOP
-- TAG-MBSBROADCASTCONFIGURATION-START
MBSBroadcastConfiguration-r17 ::= SEQUENCE {
   criticalExtensions [0] EXPLICIT CHOICE {
      mbsBroadcastConfiguration-r17 [0] MBSBroadcastConfiguration-r17-IEs,
      criticalExtensionsFuture [1] SEQUENCE {

      }
   }
}

MCCH-MessageType-r17 ::= CHOICE {
   c1 [0] EXPLICIT CHOICE {
      mbsBroadcastConfiguration-r17 [0] MBSBroadcastConfiguration-r17,
      spare1 [1] NULL
   },
   messageClassExtension [1] SEQUENCE {

   }
}

-- TAG-DL-DCCH-MESSAGE-STOP
-- TAG-MCCH-MESSAGE-START
MCCH-Message-r17 ::= SEQUENCE {
   message [0] EXPLICIT MCCH-MessageType-r17
}

PCCH-MessageType ::= CHOICE {
   c1 [0] EXPLICIT CHOICE {
      paging [0] Paging,
      spare1 [1] NULL
   },
   messageClassExtension [1] SEQUENCE {

   }
}

-- TAG-MCCH-MESSAGE-STOP
-- TAG-PCCH-PCH-MESSAGE-START
PCCH-Message ::= SEQUENCE {
   message [0] EXPLICIT PCCH-MessageType
}

InitialUE-Identity ::= CHOICE {
   ng-5G-S-TMSI-Part1 [0] BIT STRING  (SIZE (39)),
   randomValue [1] BIT STRING  (SIZE (39))
}

RRCSetupRequest-IEs ::= SEQUENCE {
   ue-Identity [0] EXPLICIT InitialUE-Identity,
   establishmentCause [1] EstablishmentCause,
   spare [2] BIT STRING  (SIZE (1))
}

-- TAG-RRCSETUPCOMPLETE-STOP
-- TAG-RRCSETUPREQUEST-START
RRCSetupRequest ::= SEQUENCE {
   rrcSetupRequest [0] RRCSetupRequest-IEs
}

RRCResumeRequest-IEs ::= SEQUENCE {
   resumeIdentity [0] ShortI-RNTI-Value,
   resumeMAC-I [1] BIT STRING  (SIZE (16)),
   resumeCause [2] ResumeCause,
   spare [3] BIT STRING  (SIZE (1))
}

-- TAG-RRCRESUMECOMPLETE-STOP
-- TAG-RRCRESUMEREQUEST-START
RRCResumeRequest ::= SEQUENCE {
   rrcResumeRequest [0] RRCResumeRequest-IEs
}

ReestabUE-Identity ::= SEQUENCE {
   c-RNTI [0] RNTI-Value,
   physCellId [1] PhysCellId,
   shortMAC-I [2] ShortMAC-I
}

RRCReestablishmentRequest-IEs ::= SEQUENCE {
   ue-Identity [0] ReestabUE-Identity,
   reestablishmentCause [1] ReestablishmentCause,
   spare [2] BIT STRING  (SIZE (1))
}

-- TAG-RRCREESTABLISHMENTCOMPLETE-STOP
-- TAG-RRCREESTABLISHMENTREQUEST-START
RRCReestablishmentRequest ::= SEQUENCE {
   rrcReestablishmentRequest [0] RRCReestablishmentRequest-IEs
}

RRCSystemInfoRequest-IEs ::= SEQUENCE {
   requested-SI-List [0] BIT STRING  (SIZE (maxSI-Message)), --32bits
   spare [1] BIT STRING  (SIZE (12))
}

RRC-PosSystemInfoRequest-r16-IEs ::= SEQUENCE {
   requestedPosSI-List [0] BIT STRING  (SIZE (maxSI-Message)), --32bits
   spare [1] BIT STRING  (SIZE (11))
}

-- TAG-RRCSETUPREQUEST-STOP
-- TAG-RRCSYSTEMINFOREQUEST-START
RRCSystemInfoRequest ::= SEQUENCE {
   criticalExtensions [0] EXPLICIT CHOICE {
      rrcSystemInfoRequest [0] RRCSystemInfoRequest-IEs,
      criticalExtensionsFuture-r16 [1] EXPLICIT CHOICE {
         rrcPosSystemInfoRequest-r16 [0] RRC-PosSystemInfoRequest-r16-IEs,
         criticalExtensionsFuture [1] SEQUENCE {

         }
      }
   }
}

UL-CCCH-MessageType ::= CHOICE {
   c1 [0] EXPLICIT CHOICE {
      rrcSetupRequest [0] RRCSetupRequest,
      rrcResumeRequest [1] RRCResumeRequest,
      rrcReestablishmentRequest [2] RRCReestablishmentRequest,
      rrcSystemInfoRequest [3] RRCSystemInfoRequest
   },
   messageClassExtension [1] SEQUENCE {

   }
}

-- TAG-PCCH-PCH-MESSAGE-STOP
-- TAG-UL-CCCH-MESSAGE-START
UL-CCCH-Message ::= SEQUENCE {
   message [0] EXPLICIT UL-CCCH-MessageType
}

RRCResumeRequest1-IEs ::= SEQUENCE {
   resumeIdentity [0] I-RNTI-Value,
   resumeMAC-I [1] BIT STRING  (SIZE (16)),
   resumeCause [2] ResumeCause,
   spare [3] BIT STRING  (SIZE (1))
}

-- TAG-RRCRESUMEREQUEST-STOP
-- TAG-RRCRESUMEREQUEST1-START
RRCResumeRequest1 ::= SEQUENCE {
   rrcResumeRequest1 [0] RRCResumeRequest1-IEs
}

UL-CCCH1-MessageType ::= CHOICE {
   c1 [0] EXPLICIT CHOICE {
      rrcResumeRequest1 [0] RRCResumeRequest1,
      spare3 [1] NULL,
      spare2 [2] NULL,
      spare1 [3] NULL
   },
   messageClassExtension [1] SEQUENCE {

   }
}

-- TAG-UL-CCCH-MESSAGE-STOP
-- TAG-UL-CCCH1-MESSAGE-START
UL-CCCH1-Message ::= SEQUENCE {
   message [0] EXPLICIT UL-CCCH1-MessageType
}

MeasQuantityResults ::= SEQUENCE {
   rsrp [0] RSRP-Range OPTIONAL,
   rsrq [1] RSRQ-Range OPTIONAL,
   sinr [2] SINR-Range OPTIONAL
}

ResultsPerSSB-Index ::= SEQUENCE {
   ssb-Index [0] SSB-Index,
   ssb-Results [1] MeasQuantityResults OPTIONAL
}

ResultsPerSSB-IndexList ::= SEQUENCE (SIZE (1..maxNrofIndexesToReport2)) OF ResultsPerSSB-Index

ResultsPerCSI-RS-Index ::= SEQUENCE {
   csi-RS-Index [0] CSI-RS-Index,
   csi-RS-Results [1] MeasQuantityResults OPTIONAL
}

ResultsPerCSI-RS-IndexList ::= SEQUENCE (SIZE (1..maxNrofIndexesToReport2)) OF ResultsPerCSI-RS-Index

-- TAG-CGI-INFOEUTRALOGGING-STOP
-- TAG-CGI-INFO-NR-START
CGI-InfoNR ::= SEQUENCE {
   plmn-IdentityInfoList [0] PLMN-IdentityInfoList OPTIONAL,
   frequencyBandList [1] MultiFrequencyBandListNR OPTIONAL,
   noSIB1 [2] SEQUENCE {
      ssb-SubcarrierOffset [0] INTEGER (0..15),
      pdcch-ConfigSIB1 [1] PDCCH-ConfigSIB1
   } OPTIONAL,
   ...,
   [[
      npn-IdentityInfoList-r16 [3] NPN-IdentityInfoList-r16 OPTIONAL
   ]],
   [[
      cellReservedForOtherUse-r16 [4] ENUMERATED { true(0) } OPTIONAL
   ]]
}

MeasResultNR ::= SEQUENCE {
   physCellId [0] PhysCellId OPTIONAL,
   measResult [1] SEQUENCE {
      cellResults [0] SEQUENCE {
         resultsSSB-Cell [0] MeasQuantityResults OPTIONAL,
         resultsCSI-RS-Cell [1] MeasQuantityResults OPTIONAL
      },
      rsIndexResults [1] SEQUENCE {
         resultsSSB-Indexes [0] ResultsPerSSB-IndexList OPTIONAL,
         resultsCSI-RS-Indexes [1] ResultsPerCSI-RS-IndexList OPTIONAL
      } OPTIONAL
   },
   ...,
   [[
      cgi-Info [2] CGI-InfoNR OPTIONAL
   ]],
   [[
      choCandidate-r17 [3] ENUMERATED { true(0) } OPTIONAL,
      choConfig-r17 [4] SEQUENCE (SIZE (1..2)) OF CondTriggerConfig-r16 OPTIONAL
         ,
      triggeredEvent-r17 [5] SEQUENCE {
         timeBetweenEvents-r17 [0] TimeBetweenEvent-r17 OPTIONAL,
         firstTriggeredEvent-r17 [1] ENUMERATED { condFirstEvent(0), 
            condSecondEvent(1) } OPTIONAL
      } OPTIONAL
   ]]
}

MeasResultServMO ::= SEQUENCE {
   servCellId [0] ServCellIndex,
   measResultServingCell [1] MeasResultNR,
   measResultBestNeighCell [2] MeasResultNR OPTIONAL,
   ...
}

MeasResultServMOList ::= SEQUENCE (SIZE (1..maxNrofServingCells)) OF MeasResultServMO

MeasResultListNR ::= SEQUENCE (SIZE (1..maxCellReport)) OF MeasResultNR

MeasQuantityResultsEUTRA ::= SEQUENCE {
   rsrp [0] RSRP-RangeEUTRA OPTIONAL,
   rsrq [1] RSRQ-RangeEUTRA OPTIONAL,
   sinr [2] SINR-RangeEUTRA OPTIONAL
}

MeasResultEUTRA ::= SEQUENCE {
   eutra-PhysCellId [0] PhysCellId,
   measResult [1] MeasQuantityResultsEUTRA,
   cgi-Info [2] CGI-InfoEUTRA OPTIONAL,
   ...
}

MeasResultListEUTRA ::= SEQUENCE (SIZE (1..maxCellReport)) OF MeasResultEUTRA

MeasResultUTRA-FDD-r16 ::= SEQUENCE {
   physCellId-r16 [0] PhysCellIdUTRA-FDD-r16,
   measResult-r16 [1] SEQUENCE {
      utra-FDD-RSCP-r16 [0] INTEGER (-5..91) OPTIONAL,
      utra-FDD-EcN0-r16 [1] INTEGER (0..49) OPTIONAL
   }
}

MeasResultListUTRA-FDD-r16 ::= SEQUENCE (SIZE (1..maxCellReport)) OF MeasResultUTRA-FDD-r16

-- TAG-MEASRESULTS-STOP
-- TAG-MEASRESULT2EUTRA-START
MeasResult2EUTRA ::= SEQUENCE {
   carrierFreq [0] ARFCN-ValueEUTRA,
   measResultServingCell [1] MeasResultEUTRA OPTIONAL,
   measResultBestNeighCell [2] MeasResultEUTRA OPTIONAL,
   ...
}

MeasResultServFreqListEUTRA-SCG ::= SEQUENCE (SIZE (1..maxNrofServingCellsEUTRA)) OF MeasResult2EUTRA

-- TAG-MEASRESULT2EUTRA-STOP
-- TAG-MEASRESULT2NR-START
MeasResult2NR ::= SEQUENCE {
   ssbFrequency [0] ARFCN-ValueNR OPTIONAL,
   refFreqCSI-RS [1] ARFCN-ValueNR OPTIONAL,
   measResultServingCell [2] MeasResultNR OPTIONAL,
   measResultNeighCellListNR [3] MeasResultListNR OPTIONAL,
   ...
}

MeasResultServFreqListNR-SCG ::= SEQUENCE (SIZE (1..maxNrofServingCells)) OF MeasResult2NR

MeasResultSFTD-EUTRA ::= SEQUENCE {
   eutra-PhysCellId [0] EUTRA-PhysCellId,
   sfn-OffsetResult [1] INTEGER (0..1023),
   frameBoundaryOffsetResult [2] INTEGER (-30720..30719),
   rsrp-Result [3] RSRP-Range OPTIONAL
}

MeasResultCellSFTD-NR ::= SEQUENCE {
   physCellId [0] PhysCellId,
   sfn-OffsetResult [1] INTEGER (0..1023),
   frameBoundaryOffsetResult [2] INTEGER (-30720..30719),
   rsrp-Result [3] RSRP-Range OPTIONAL
}

-- TAG-MEASOBJECTUTRA-FDD-STOP
-- TAG-MEASRESULTCELLLISTSFTD-NR-START
MeasResultCellListSFTD-NR ::= SEQUENCE (SIZE (1..maxCellSFTD)) OF MeasResultCellSFTD-NR

MeasResultForRSSI-r16 ::= SEQUENCE {
   rssi-Result-r16 [0] RSSI-Range-r16,
   channelOccupancy-r16 [1] INTEGER (0..100)
}

-- TAG-CODEBOOKCONFIG-STOP
-- TAG-COMMONLOCATIONINFO-START
CommonLocationInfo-r16 ::= SEQUENCE {
   gnss-TOD-msec-r16 [0] OCTET STRING OPTIONAL,
   locationTimestamp-r16 [1] OCTET STRING OPTIONAL,
   locationCoordinate-r16 [2] OCTET STRING OPTIONAL,
   locationError-r16 [3] OCTET STRING OPTIONAL,
   locationSource-r16 [4] OCTET STRING OPTIONAL,
   velocityEstimate-r16 [5] OCTET STRING OPTIONAL
}

LogMeasResultBT-r16 ::= SEQUENCE {
   bt-Addr-r16 [0] BIT STRING  (SIZE (48)),
   rssi-BT-r16 [1] INTEGER (-128..127) OPTIONAL,
   ...
}

-- TAG-LOGGINGINTERVAL-STOP
-- TAG-LOGMEASRESULTLISTBT-START
LogMeasResultListBT-r16 ::= SEQUENCE (SIZE (1..maxBT-IdReport-r16)) OF LogMeasResultBT-r16

WLAN-Identifiers-r16 ::= SEQUENCE {
   ssid-r16 [0] OCTET STRING (SIZE (1..32)) OPTIONAL,
   bssid-r16 [1] OCTET STRING (SIZE (6)) OPTIONAL,
   hessid-r16 [2] OCTET STRING (SIZE (6)) OPTIONAL,
   ...
}

WLAN-RTT-r16 ::= SEQUENCE {
   rttValue-r16 [0] INTEGER (0..16777215),
   rttUnits-r16 [1] ENUMERATED { microseconds(0), hundredsofnanoseconds(1), 
      tensofnanoseconds(2), nanoseconds(3), tenthsofnanoseconds(4), ... },
   rttAccuracy-r16 [2] INTEGER (0..255) OPTIONAL,
   ...
}

LogMeasResultWLAN-r16 ::= SEQUENCE {
   wlan-Identifiers-r16 [0] WLAN-Identifiers-r16,
   rssiWLAN-r16 [1] WLAN-RSSI-Range-r16 OPTIONAL,
   rtt-WLAN-r16 [2] WLAN-RTT-r16 OPTIONAL,
   ...
}

-- TAG-LOGMEASRESULTLISTBT-STOP
-- TAG-LOGMEASRESULTLISTWLAN-START
LogMeasResultListWLAN-r16 ::= SEQUENCE (SIZE (1..maxWLAN-Id-Report-r16)) OF LogMeasResultWLAN-r16

-- TAG-SEMISTATICCHANNELACCESSCONFIGUE-STOP
-- TAG-SENSORLOCATIONINFO-START
Sensor-LocationInfo-r16 ::= SEQUENCE {
   sensor-MeasurementInformation-r16 [0] OCTET STRING OPTIONAL,
   sensor-MotionInformation-r16 [1] OCTET STRING OPTIONAL,
   ...
}

-- TAG-LBT-FAILURERECOVERYCONFIG-STOP
-- TAG-LOCATIONINFO-START
LocationInfo-r16 ::= SEQUENCE {
   commonLocationInfo-r16 [0] CommonLocationInfo-r16 OPTIONAL,
   bt-LocationInfo-r16 [1] LogMeasResultListBT-r16 OPTIONAL,
   wlan-LocationInfo-r16 [2] LogMeasResultListWLAN-r16 OPTIONAL,
   sensor-LocationInfo-r16 [3] Sensor-LocationInfo-r16 OPTIONAL,
   ...
}

UL-PDCP-DelayValueResult-r16 ::= SEQUENCE {
   drb-Id-r16 [0] DRB-Identity,
   averageDelay-r16 [1] INTEGER (0..10000),
   ...
}

UL-PDCP-DelayValueResultList-r16 ::= SEQUENCE (SIZE (1..maxDRB)) OF 
   UL-PDCP-DelayValueResult-r16

MeasResultCBR-NR-r16 ::= SEQUENCE {
   sl-poolReportIdentity-r16 [0] SL-ResourcePoolID-r16,
   sl-CBR-ResultsNR-r16 [1] SL-CBR-r16,
   ...
}

MeasResultNR-SL-r16 ::= SEQUENCE {
   measResultListCBR-NR-r16 [0] SEQUENCE (SIZE (1..maxNrofSL-PoolToMeasureNR-r16)) OF MeasResultCBR-NR-r16,
   ...
}

-- TAG-MEASRESULTSCG-FAILURE-STOP
-- TAG-MEASRESULTSSL-START
MeasResultsSL-r16 ::= SEQUENCE {
   measResultsListSL-r16 [0] EXPLICIT CHOICE {
      measResultNR-SL-r16 [0] MeasResultNR-SL-r16,
      ...
   },
   ...
}

MeasResultSRS-RSRP-r16 ::= SEQUENCE {
   srs-ResourceId-r16 [0] SRS-ResourceId,
   srs-RSRP-Result-r16 [1] SRS-RSRP-Range-r16
}

MeasResultListSRS-RSRP-r16 ::= SEQUENCE (SIZE (1..maxCLI-Report-r16)) OF MeasResultSRS-RSRP-r16

MeasResultCLI-RSSI-r16 ::= SEQUENCE {
   rssi-ResourceId-r16 [0] RSSI-ResourceId-r16,
   cli-RSSI-Result-r16 [1] CLI-RSSI-Range-r16
}

MeasResultListCLI-RSSI-r16 ::= SEQUENCE (SIZE (1..maxCLI-Report-r16)) OF MeasResultCLI-RSSI-r16

MeasResultCLI-r16 ::= SEQUENCE {
   measResultListSRS-RSRP-r16 [0] MeasResultListSRS-RSRP-r16 OPTIONAL,
   measResultListCLI-RSSI-r16 [1] MeasResultListCLI-RSSI-r16 OPTIONAL
}

-- TAG-MEASRESULTIDLENR-STOP
-- TAG-MEASRESULTRXTXTIMEDIFF-START
MeasResultRxTxTimeDiff-r17 ::= SEQUENCE {
   rxTxTimeDiff-ue-r17 [0] RxTxTimeDiff-r17 OPTIONAL,
   ...
}

UL-PDCP-ExcessDelayResult-r17 ::= SEQUENCE {
   drb-Id-r17 [0] DRB-Identity,
   excessDelay-r17 [1] INTEGER (0..31),
   ...
}

UL-PDCP-ExcessDelayResultList-r17 ::= SEQUENCE (SIZE (1..maxDRB)) OF 
   UL-PDCP-ExcessDelayResult-r17

-- TAG-MEASRESULTCELLLISTSFTD-EUTRA-STOP
-- TAG-MEASRESULTS-START
MeasResults ::= SEQUENCE {
   measId [0] MeasId,
   measResultServingMOList [1] MeasResultServMOList,
   measResultNeighCells [2] EXPLICIT CHOICE {
      measResultListNR [0] MeasResultListNR,
      ...,
      measResultListEUTRA [1] MeasResultListEUTRA,
      measResultListUTRA-FDD-r16 [2] MeasResultListUTRA-FDD-r16,
      sl-MeasResultsCandRelay-r17 [3] OCTET STRING
   } OPTIONAL,
   ...,
   [[
      measResultServFreqListEUTRA-SCG [3] MeasResultServFreqListEUTRA-SCG
          OPTIONAL,
      measResultServFreqListNR-SCG [4] MeasResultServFreqListNR-SCG OPTIONAL,
      measResultSFTD-EUTRA [5] MeasResultSFTD-EUTRA OPTIONAL,
      measResultSFTD-NR [6] MeasResultCellSFTD-NR OPTIONAL
   ]],
   [[
      measResultCellListSFTD-NR [7] MeasResultCellListSFTD-NR OPTIONAL
   ]],
   [[
      measResultForRSSI-r16 [8] MeasResultForRSSI-r16 OPTIONAL,
      locationInfo-r16 [9] LocationInfo-r16 OPTIONAL,
      ul-PDCP-DelayValueResultList-r16 [10] UL-PDCP-DelayValueResultList-r16
          OPTIONAL,
      measResultsSL-r16 [11] MeasResultsSL-r16 OPTIONAL,
      measResultCLI-r16 [12] MeasResultCLI-r16 OPTIONAL
   ]],
   [[
      measResultRxTxTimeDiff-r17 [13] MeasResultRxTxTimeDiff-r17 OPTIONAL,
      sl-MeasResultServingRelay-r17 [14] OCTET STRING OPTIONAL,
      ul-PDCP-ExcessDelayResultList-r17 [15] UL-PDCP-ExcessDelayResultList-r17
          OPTIONAL,
      coarseLocationInfo-r17 [16] OCTET STRING OPTIONAL
   ]]
}

MeasurementReport-IEs ::= SEQUENCE {
   measResults [0] MeasResults,
   lateNonCriticalExtension [1] OCTET STRING OPTIONAL,
   nonCriticalExtension [2] SEQUENCE {

   } OPTIONAL
}

-- TAG-MCGFAILUREINFORMATION-STOP
-- TAG-MEASUREMENTREPORT-START
MeasurementReport ::= SEQUENCE {
   criticalExtensions [0] EXPLICIT CHOICE {
      measurementReport [0] MeasurementReport-IEs,
      criticalExtensionsFuture [1] SEQUENCE {

      }
   }
}

UplinkTxDirectCurrentBWP ::= SEQUENCE {
   bwp-Id [0] BWP-Id,
   shift7dot5kHz [1] BOOLEAN,
   txDirectCurrentLocation [2] INTEGER (0..3301)
}

UplinkTxDirectCurrentCell ::= SEQUENCE {
   servCellIndex [0] ServCellIndex,
   uplinkDirectCurrentBWP [1] SEQUENCE (SIZE (1..maxNrofBWPs)) OF UplinkTxDirectCurrentBWP,
   ...,
   [[
      uplinkDirectCurrentBWP-SUL [2] SEQUENCE (SIZE (1..maxNrofBWPs)) OF 
         UplinkTxDirectCurrentBWP OPTIONAL
   ]]
}

-- TAG-UU-RELAYRLC-CHANNELID-STOP
-- TAG-UPLINKTXDIRECTCURRENTLIST-START
UplinkTxDirectCurrentList ::= SEQUENCE (SIZE (1..maxNrofServingCells)) OF UplinkTxDirectCurrentCell
   

-- TAG-TRACEREFERENCE-STOP
-- TAG-UE-MeasurementsAvailable-START
UE-MeasurementsAvailable-r16 ::= SEQUENCE {
   logMeasAvailable-r16 [0] ENUMERATED { true(0) } OPTIONAL,
   logMeasAvailableBT-r16 [1] ENUMERATED { true(0) } OPTIONAL,
   logMeasAvailableWLAN-r16 [2] ENUMERATED { true(0) } OPTIONAL,
   connEstFailInfoAvailable-r16 [3] ENUMERATED { true(0) } OPTIONAL,
   rlf-InfoAvailable-r16 [4] ENUMERATED { true(0) } OPTIONAL,
   ...,
   [[
      successHO-InfoAvailable-r17 [5] ENUMERATED { true(0) } OPTIONAL,
      sigLogMeasConfigAvailable-r17 [6] BOOLEAN OPTIONAL
   ]]
}

NeedForGapsIntraFreq-r16 ::= SEQUENCE {
   servCellId-r16 [0] ServCellIndex,
   gapIndicationIntra-r16 [1] ENUMERATED { gap(0), no-gap(1) }
}

NeedForGapsIntraFreqList-r16 ::= SEQUENCE (SIZE (1..maxNrofServingCells)) OF 
   NeedForGapsIntraFreq-r16

NeedForGapsNR-r16 ::= SEQUENCE {
   bandNR-r16 [0] FreqBandIndicatorNR,
   gapIndication-r16 [1] ENUMERATED { gap(0), no-gap(1) }
}

NeedForGapsBandListNR-r16 ::= SEQUENCE (SIZE (1..maxBands)) OF NeedForGapsNR-r16

-- TAG-NeedForGapsConfigNR-STOP
-- TAG-NeedForGapsInfoNR-START
NeedForGapsInfoNR-r16 ::= SEQUENCE {
   intraFreq-needForGap-r16 [0] NeedForGapsIntraFreqList-r16,
   interFreq-needForGap-r16 [1] NeedForGapsBandListNR-r16
}

UplinkTxDirectCurrentCarrierInfo-r16 ::= SEQUENCE {
   servCellIndex-r16 [0] ServCellIndex,
   servCellInfo-r16 [1] EXPLICIT CHOICE {
      bwp-Id-r16 [0] BWP-Id,
      deactivatedCarrier-r16 [1] ENUMERATED { deactivated(0) }
   }
}

UplinkTxDirectCurrentTwoCarrierInfo-r16 ::= SEQUENCE {
   referenceCarrierIndex-r16 [0] ServCellIndex,
   shift7dot5kHz-r16 [1] BOOLEAN,
   txDirectCurrentLocation-r16 [2] INTEGER (0..3301)
}

UplinkTxDirectCurrentTwoCarrier-r16 ::= SEQUENCE {
   carrierOneInfo-r16 [0] UplinkTxDirectCurrentCarrierInfo-r16,
   carrierTwoInfo-r16 [1] UplinkTxDirectCurrentCarrierInfo-r16,
   singlePA-TxDirectCurrent-r16 [2] UplinkTxDirectCurrentTwoCarrierInfo-r16,
   secondPA-TxDirectCurrent-r16 [3] UplinkTxDirectCurrentTwoCarrierInfo-r16
       OPTIONAL
}

-- TAG-UPLINKTXDIRECTCURRENTMORECARRIERLIST-STOP
-- TAG-UPLINKTXDIRECTCURRENTTWOCARRIERLIST-START
UplinkTxDirectCurrentTwoCarrierList-r16 ::= SEQUENCE (SIZE (1..maxNrofTxDC-TwoCarrier-r16)) OF 
   UplinkTxDirectCurrentTwoCarrier-r16

NeedForNCSG-IntraFreq-r17 ::= SEQUENCE {
   servCellId-r17 [0] ServCellIndex,
   gapIndicationIntra-r17 [1] ENUMERATED { gap(0), ncsg(1), nogap-noncsg(2) }
}

NeedForNCSG-IntraFreqList-r17 ::= SEQUENCE (SIZE (1..maxNrofServingCells)) OF 
   NeedForNCSG-IntraFreq-r17

NeedForNCSG-NR-r17 ::= SEQUENCE {
   bandNR-r17 [0] FreqBandIndicatorNR,
   gapIndication-r17 [1] ENUMERATED { gap(0), ncsg(1), nogap-noncsg(2) }
}

NeedForNCSG-BandListNR-r17 ::= SEQUENCE (SIZE (1..maxBands)) OF NeedForNCSG-NR-r17

-- TAG-NEEDFORGAPNCSG-INFOEUTRA-STOP
-- TAG-NEEDFORGAPNCSG-INFONR-START
NeedForGapNCSG-InfoNR-r17 ::= SEQUENCE {
   intraFreq-needForNCSG-r17 [0] NeedForNCSG-IntraFreqList-r17,
   interFreq-needForNCSG-r17 [1] NeedForNCSG-BandListNR-r17
}

NeedForNCSG-EUTRA-r17 ::= SEQUENCE {
   bandEUTRA-r17 [0] FreqBandIndicatorEUTRA,
   gapIndication-r17 [1] ENUMERATED { gap(0), ncsg(1), nogap-noncsg(2) }
}

-- TAG-NEEDFORGAPNCSG-CONFIGNR-STOP
-- TAG-NEEDFORGAPNCSG-INFOEUTRA-START
NeedForGapNCSG-InfoEUTRA-r17 ::= SEQUENCE {
   needForNCSG-EUTRA-r17 [0] SEQUENCE (SIZE (1..maxBandsEUTRA)) OF NeedForNCSG-EUTRA-r17
}

DefaultDC-Location-r17 ::= CHOICE {
   ul [0] FrequencyComponent-r17,
   dl [1] FrequencyComponent-r17,
   ulAndDL [2] FrequencyComponent-r17
}

OffsetValue-r17 ::= SEQUENCE {
   offsetValue-r17 [0] INTEGER (-20000..20000),
   shift7dot5kHz-r17 [1] BOOLEAN
}

CC-Group-r17 ::= SEQUENCE {
   servCellIndexLower-r17 [0] ServCellIndex,
   servCellIndexHigher-r17 [1] ServCellIndex OPTIONAL,
   defaultDC-Location-r17 [2] EXPLICIT DefaultDC-Location-r17,
   offsetToDefault-r17 [3] EXPLICIT CHOICE {
      offsetValue [0] OffsetValue-r17,
      offsetlist [1] SEQUENCE (SIZE (1..maxNrofReqComDC-Location-r17)) OF OffsetValue-r17
   } OPTIONAL
}

-- TAG-UPLINKTXDIRECTCURRENTLIST-STOP
-- TAG-UPLINKTXDIRECTCURRENTMORECARRIERLIST-START
UplinkTxDirectCurrentMoreCarrierList-r17 ::= SEQUENCE (SIZE (1..maxNrofCC-Group-r17)) OF 
   CC-Group-r17

RRCReconfigurationComplete-v1720-IEs ::= SEQUENCE {
   uplinkTxDirectCurrentMoreCarrierList-r17 [0] 
      UplinkTxDirectCurrentMoreCarrierList-r17 OPTIONAL,
   nonCriticalExtension [1] SEQUENCE {

   } OPTIONAL
}

RRCReconfigurationComplete-v1700-IEs ::= SEQUENCE {
   needForGapNCSG-InfoNR-r17 [0] NeedForGapNCSG-InfoNR-r17 OPTIONAL,
   needForGapNCSG-InfoEUTRA-r17 [1] NeedForGapNCSG-InfoEUTRA-r17 OPTIONAL,
   selectedCondRRCReconfig-r17 [2] CondReconfigId-r16 OPTIONAL,
   nonCriticalExtension [3] RRCReconfigurationComplete-v1720-IEs OPTIONAL
}

RRCReconfigurationComplete-v1640-IEs ::= SEQUENCE {
   uplinkTxDirectCurrentTwoCarrierList-r16 [0] 
      UplinkTxDirectCurrentTwoCarrierList-r16 OPTIONAL,
   nonCriticalExtension [1] RRCReconfigurationComplete-v1700-IEs OPTIONAL
}

RRCReconfigurationComplete-v1610-IEs ::= SEQUENCE {
   ue-MeasurementsAvailable-r16 [0] UE-MeasurementsAvailable-r16 OPTIONAL,
   needForGapsInfoNR-r16 [1] NeedForGapsInfoNR-r16 OPTIONAL,
   nonCriticalExtension [2] RRCReconfigurationComplete-v1640-IEs OPTIONAL
}

RRCReconfigurationComplete-v1560-IEs ::= SEQUENCE {
   scg-Response [0] EXPLICIT CHOICE {
      nr-SCG-Response [0] OCTET STRING (CONTAINING RRCReconfigurationComplete),
      eutra-SCG-Response [1] OCTET STRING
   } OPTIONAL,
   nonCriticalExtension [1] RRCReconfigurationComplete-v1610-IEs OPTIONAL
}

RRCReconfigurationComplete-v1530-IEs ::= SEQUENCE {
   uplinkTxDirectCurrentList [0] UplinkTxDirectCurrentList OPTIONAL,
   nonCriticalExtension [1] RRCReconfigurationComplete-v1560-IEs OPTIONAL
}

RRCReconfigurationComplete-IEs ::= SEQUENCE {
   lateNonCriticalExtension [0] OCTET STRING OPTIONAL,
   nonCriticalExtension [1] RRCReconfigurationComplete-v1530-IEs OPTIONAL
}

-- TAG-RRCRECONFIGURATION-STOP
-- TAG-RRCRECONFIGURATIONCOMPLETE-START
RRCReconfigurationComplete ::= SEQUENCE {
   rrc-TransactionIdentifier [0] RRC-TransactionIdentifier,
   criticalExtensions [1] EXPLICIT CHOICE {
      rrcReconfigurationComplete [0] RRCReconfigurationComplete-IEs,
      criticalExtensionsFuture [1] SEQUENCE {

      }
   }
}

RegisteredAMF ::= SEQUENCE {
   plmn-Identity [0] PLMN-Identity OPTIONAL,
   amf-Identifier [1] AMF-Identifier
}

-- TAG-SLOTFORMATINDICATOR-STOP
-- TAG-S-NSSAI-START
S-NSSAI ::= CHOICE {
   sst [0] BIT STRING  (SIZE (8)),
   sst-SD [1] BIT STRING  (SIZE (32))
}

RRCSetupComplete-v1700-IEs ::= SEQUENCE {
   onboardingRequest-r17 [0] ENUMERATED { true(0) } OPTIONAL,
   nonCriticalExtension [1] SEQUENCE {

   } OPTIONAL
}

RRCSetupComplete-v1690-IEs ::= SEQUENCE {
   ul-RRC-Segmentation-r16 [0] ENUMERATED { true(0) } OPTIONAL,
   nonCriticalExtension [1] RRCSetupComplete-v1700-IEs OPTIONAL
}

RRCSetupComplete-v1610-IEs ::= SEQUENCE {
   iab-NodeIndication-r16 [0] ENUMERATED { true(0) } OPTIONAL,
   idleMeasAvailable-r16 [1] ENUMERATED { true(0) } OPTIONAL,
   ue-MeasurementsAvailable-r16 [2] UE-MeasurementsAvailable-r16 OPTIONAL,
   mobilityHistoryAvail-r16 [3] ENUMERATED { true(0) } OPTIONAL,
   mobilityState-r16 [4] ENUMERATED { normal(0), medium(1), high(2), spare(3) }
       OPTIONAL,
   nonCriticalExtension [5] RRCSetupComplete-v1690-IEs OPTIONAL
}

RRCSetupComplete-IEs ::= SEQUENCE {
   selectedPLMN-Identity [0] INTEGER (1..maxPLMN),
   registeredAMF [1] RegisteredAMF OPTIONAL,
   guami-Type [2] ENUMERATED { native(0), mapped(1) } OPTIONAL,
   s-NSSAI-List [3] SEQUENCE (SIZE (1..maxNrofS-NSSAI)) OF S-NSSAI OPTIONAL,
   dedicatedNAS-Message [4] DedicatedNAS-Message,
   ng-5G-S-TMSI-Value [5] EXPLICIT CHOICE {
      ng-5G-S-TMSI [0] NG-5G-S-TMSI,
      ng-5G-S-TMSI-Part2 [1] BIT STRING  (SIZE (9))
   } OPTIONAL,
   lateNonCriticalExtension [6] OCTET STRING OPTIONAL,
   nonCriticalExtension [7] RRCSetupComplete-v1610-IEs OPTIONAL
}

-- TAG-RRCSETUP-STOP
-- TAG-RRCSETUPCOMPLETE-START
RRCSetupComplete ::= SEQUENCE {
   rrc-TransactionIdentifier [0] RRC-TransactionIdentifier,
   criticalExtensions [1] EXPLICIT CHOICE {
      rrcSetupComplete [0] RRCSetupComplete-IEs,
      criticalExtensionsFuture [1] SEQUENCE {

      }
   }
}

RRCReestablishmentComplete-v1610-IEs ::= SEQUENCE {
   ue-MeasurementsAvailable-r16 [0] UE-MeasurementsAvailable-r16 OPTIONAL,
   nonCriticalExtension [1] SEQUENCE {

   } OPTIONAL
}

RRCReestablishmentComplete-IEs ::= SEQUENCE {
   lateNonCriticalExtension [0] OCTET STRING OPTIONAL,
   nonCriticalExtension [1] RRCReestablishmentComplete-v1610-IEs OPTIONAL
}

-- TAG-RRCREESTABLISHMENT-STOP
-- TAG-RRCREESTABLISHMENTCOMPLETE-START
RRCReestablishmentComplete ::= SEQUENCE {
   rrc-TransactionIdentifier [0] RRC-TransactionIdentifier,
   criticalExtensions [1] EXPLICIT CHOICE {
      rrcReestablishmentComplete [0] RRCReestablishmentComplete-IEs,
      criticalExtensionsFuture [1] SEQUENCE {

      }
   }
}

MeasResultsPerCellIdleEUTRA-r16 ::= SEQUENCE {
   eutra-PhysCellId-r16 [0] EUTRA-PhysCellId,
   measIdleResultEUTRA-r16 [1] SEQUENCE {
      rsrp-ResultEUTRA-r16 [0] RSRP-RangeEUTRA OPTIONAL,
      rsrq-ResultEUTRA-r16 [1] RSRQ-RangeEUTRA-r16 OPTIONAL
   },
   ...
}

MeasResultsPerCarrierIdleEUTRA-r16 ::= SEQUENCE {
   carrierFreqEUTRA-r16 [0] ARFCN-ValueEUTRA,
   measResultsPerCellListIdleEUTRA-r16 [1] SEQUENCE (SIZE (1..maxCellMeasIdle-r16)) OF 
      MeasResultsPerCellIdleEUTRA-r16,
   ...
}

-- TAG-MEASRESULT2NR-STOP
-- TAG-MEASRESULTIDLEEUTRA-START
MeasResultIdleEUTRA-r16 ::= SEQUENCE {
   measResultsPerCarrierListIdleEUTRA-r16 [0] SEQUENCE (SIZE (1..maxFreqIdle-r16)) OF 
      MeasResultsPerCarrierIdleEUTRA-r16,
   ...
}

ResultsPerSSB-IndexIdle-r16 ::= SEQUENCE {
   ssb-Index-r16 [0] SSB-Index,
   ssb-Results-r16 [1] SEQUENCE {
      ssb-RSRP-Result-r16 [0] RSRP-Range OPTIONAL,
      ssb-RSRQ-Result-r16 [1] RSRQ-Range OPTIONAL
   } OPTIONAL
}

ResultsPerSSB-IndexList-r16 ::= SEQUENCE (SIZE (1..maxNrofIndexesToReport)) OF 
   ResultsPerSSB-IndexIdle-r16

MeasResultsPerCellIdleNR-r16 ::= SEQUENCE {
   physCellId-r16 [0] PhysCellId,
   measIdleResultNR-r16 [1] SEQUENCE {
      rsrp-Result-r16 [0] RSRP-Range OPTIONAL,
      rsrq-Result-r16 [1] RSRQ-Range OPTIONAL,
      resultsSSB-Indexes-r16 [2] ResultsPerSSB-IndexList-r16 OPTIONAL
   },
   ...
}

MeasResultsPerCarrierIdleNR-r16 ::= SEQUENCE {
   carrierFreq-r16 [0] ARFCN-ValueNR,
   measResultsPerCellListIdleNR-r16 [1] SEQUENCE (SIZE (1..maxCellMeasIdle-r16)) OF 
      MeasResultsPerCellIdleNR-r16,
   ...
}

-- TAG-MEASRESULTIDLEEUTRA-STOP
-- TAG-MEASRESULTIDLENR-START
MeasResultIdleNR-r16 ::= SEQUENCE {
   measResultServingCell-r16 [0] SEQUENCE {
      rsrp-Result-r16 [0] RSRP-Range OPTIONAL,
      rsrq-Result-r16 [1] RSRQ-Range OPTIONAL,
      resultsSSB-Indexes-r16 [2] ResultsPerSSB-IndexList-r16 OPTIONAL
   },
   measResultsPerCarrierListIdleNR-r16 [1] SEQUENCE (SIZE (1..maxFreqIdle-r16)) OF 
      MeasResultsPerCarrierIdleNR-r16 OPTIONAL,
   ...
}

RRCResumeComplete-v1720-IEs ::= SEQUENCE {
   uplinkTxDirectCurrentMoreCarrierList-r17 [0] 
      UplinkTxDirectCurrentMoreCarrierList-r17 OPTIONAL,
   nonCriticalExtension [1] SEQUENCE {

   } OPTIONAL
}

RRCResumeComplete-v1700-IEs ::= SEQUENCE {
   needForGapNCSG-InfoNR-r17 [0] NeedForGapNCSG-InfoNR-r17 OPTIONAL,
   needForGapNCSG-InfoEUTRA-r17 [1] NeedForGapNCSG-InfoEUTRA-r17 OPTIONAL,
   nonCriticalExtension [2] RRCResumeComplete-v1720-IEs OPTIONAL
}

RRCResumeComplete-v1640-IEs ::= SEQUENCE {
   uplinkTxDirectCurrentTwoCarrierList-r16 [0] 
      UplinkTxDirectCurrentTwoCarrierList-r16 OPTIONAL,
   nonCriticalExtension [1] RRCResumeComplete-v1700-IEs OPTIONAL
}

RRCResumeComplete-v1610-IEs ::= SEQUENCE {
   idleMeasAvailable-r16 [0] ENUMERATED { true(0) } OPTIONAL,
   measResultIdleEUTRA-r16 [1] MeasResultIdleEUTRA-r16 OPTIONAL,
   measResultIdleNR-r16 [2] MeasResultIdleNR-r16 OPTIONAL,
   scg-Response-r16 [3] EXPLICIT CHOICE {
      nr-SCG-Response [0] OCTET STRING (CONTAINING RRCReconfigurationComplete),
      eutra-SCG-Response [1] OCTET STRING
   } OPTIONAL,
   ue-MeasurementsAvailable-r16 [4] UE-MeasurementsAvailable-r16 OPTIONAL,
   mobilityHistoryAvail-r16 [5] ENUMERATED { true(0) } OPTIONAL,
   mobilityState-r16 [6] ENUMERATED { normal(0), medium(1), high(2), spare(3) }
       OPTIONAL,
   needForGapsInfoNR-r16 [7] NeedForGapsInfoNR-r16 OPTIONAL,
   nonCriticalExtension [8] RRCResumeComplete-v1640-IEs OPTIONAL
}

RRCResumeComplete-IEs ::= SEQUENCE {
   dedicatedNAS-Message [0] DedicatedNAS-Message OPTIONAL,
   selectedPLMN-Identity [1] INTEGER (1..maxPLMN) OPTIONAL,
   uplinkTxDirectCurrentList [2] UplinkTxDirectCurrentList OPTIONAL,
   lateNonCriticalExtension [3] OCTET STRING OPTIONAL,
   nonCriticalExtension [4] RRCResumeComplete-v1610-IEs OPTIONAL
}

-- TAG-RRCRESUME-STOP
-- TAG-RRCRESUMECOMPLETE-START
RRCResumeComplete ::= SEQUENCE {
   rrc-TransactionIdentifier [0] RRC-TransactionIdentifier,
   criticalExtensions [1] EXPLICIT CHOICE {
      rrcResumeComplete [0] RRCResumeComplete-IEs,
      criticalExtensionsFuture [1] SEQUENCE {

      }
   }
}

SecurityModeComplete-IEs ::= SEQUENCE {
   lateNonCriticalExtension [0] OCTET STRING OPTIONAL,
   nonCriticalExtension [1] SEQUENCE {

   } OPTIONAL
}

-- TAG-SECURITYMODECOMMAND-STOP
-- TAG-SECURITYMODECOMPLETE-START
SecurityModeComplete ::= SEQUENCE {
   rrc-TransactionIdentifier [0] RRC-TransactionIdentifier,
   criticalExtensions [1] EXPLICIT CHOICE {
      securityModeComplete [0] SecurityModeComplete-IEs,
      criticalExtensionsFuture [1] SEQUENCE {

      }
   }
}

SecurityModeFailure-IEs ::= SEQUENCE {
   lateNonCriticalExtension [0] OCTET STRING OPTIONAL,
   nonCriticalExtension [1] SEQUENCE {

   } OPTIONAL
}

-- TAG-SECURITYMODECOMPLETE-STOP
-- TAG-SECURITYMODEFAILURE-START
SecurityModeFailure ::= SEQUENCE {
   rrc-TransactionIdentifier [0] RRC-TransactionIdentifier,
   criticalExtensions [1] EXPLICIT CHOICE {
      securityModeFailure [0] SecurityModeFailure-IEs,
      criticalExtensionsFuture [1] SEQUENCE {

      }
   }
}

ULInformationTransfer-v1700-IEs ::= SEQUENCE {
   dedicatedInfoF1c-r17 [0] DedicatedInfoF1c-r17 OPTIONAL,
   nonCriticalExtension [1] SEQUENCE {

   } OPTIONAL
}

ULInformationTransfer-IEs ::= SEQUENCE {
   dedicatedNAS-Message [0] DedicatedNAS-Message OPTIONAL,
   lateNonCriticalExtension [1] OCTET STRING OPTIONAL,
   nonCriticalExtension [2] ULInformationTransfer-v1700-IEs OPTIONAL
}

-- TAG-ULDEDICATEDMESSAGESEGMENT-STOP
-- TAG-ULINFORMATIONTRANSFER-START
ULInformationTransfer ::= SEQUENCE {
   criticalExtensions [0] EXPLICIT CHOICE {
      ulInformationTransfer [0] ULInformationTransfer-IEs,
      criticalExtensionsFuture [1] SEQUENCE {

      }
   }
}

EUTRA-RSTD-Info ::= SEQUENCE {
   carrierFreq [0] ARFCN-ValueEUTRA,
   measPRS-Offset [1] INTEGER (0..39),
   ...
}

EUTRA-RSTD-InfoList ::= SEQUENCE (SIZE (1..maxInterRAT-RSTD-Freq)) OF EUTRA-RSTD-Info

NR-PRS-MeasurementInfo-r16 ::= SEQUENCE {
   dl-PRS-PointA-r16 [0] ARFCN-ValueNR,
   nr-MeasPRS-RepetitionAndOffset-r16 [1] EXPLICIT CHOICE {
      ms20-r16 [0] INTEGER (0..19),
      ms40-r16 [1] INTEGER (0..39),
      ms80-r16 [2] INTEGER (0..79),
      ms160-r16 [3] INTEGER (0..159),
      ...
   },
   nr-MeasPRS-length-r16 [2] ENUMERATED { ms1dot5(0), ms3(1), ms3dot5(2), 
      ms4(3), ms5dot5(4), ms6(5), ms10(6), ms20(7) },
   ...
}

NR-PRS-MeasurementInfoList-r16 ::= SEQUENCE (SIZE (1..maxFreqLayers)) OF 
   NR-PRS-MeasurementInfo-r16

-- TAG-LOCATIONINFO-STOP
-- TAG-LOCATIONMEASUREMENTINFO-START
LocationMeasurementInfo ::= CHOICE {
   eutra-RSTD [0] EUTRA-RSTD-InfoList,
   ...,
   eutra-FineTimingDetection [1] NULL,
   nr-PRS-Measurement-r16 [2] NR-PRS-MeasurementInfoList-r16
}

LocationMeasurementIndication-IEs ::= SEQUENCE {
   measurementIndication [0] EXPLICIT CHOICE {
      release [0] NULL,
      setup [1] EXPLICIT LocationMeasurementInfo
   },
   lateNonCriticalExtension [1] OCTET STRING OPTIONAL,
   nonCriticalExtension [2] SEQUENCE {

   } OPTIONAL
}

-- TAG-IABOTHERINFORMATION-STOP
-- TAG-LOCATIONMEASUREMENTINDICATION-START
LocationMeasurementIndication ::= SEQUENCE {
   criticalExtensions [0] EXPLICIT CHOICE {
      locationMeasurementIndication [0] LocationMeasurementIndication-IEs,
      criticalExtensionsFuture [1] SEQUENCE {

      }
   }
}

UE-CapabilityRAT-Container ::= SEQUENCE {
   rat-Type [0] RAT-Type,
   ue-CapabilityRAT-Container [1] OCTET STRING
}

-- TAG-UE-BASEDPERFMEAS-PARAMETERS-STOP
-- TAG-UE-CAPABILITYRAT-CONTAINERLIST-START
UE-CapabilityRAT-ContainerList ::= SEQUENCE (SIZE (0..maxRAT-CapabilityContainers)) OF 
   UE-CapabilityRAT-Container

UECapabilityInformation-IEs ::= SEQUENCE {
   ue-CapabilityRAT-ContainerList [0] UE-CapabilityRAT-ContainerList OPTIONAL,
   lateNonCriticalExtension [1] OCTET STRING OPTIONAL,
   nonCriticalExtension [2] SEQUENCE {

   } OPTIONAL
}

-- TAG-UECAPABILITYENQUIRY-STOP
-- TAG-UECAPABILITYINFORMATION-START
UECapabilityInformation ::= SEQUENCE {
   rrc-TransactionIdentifier [0] RRC-TransactionIdentifier,
   criticalExtensions [1] EXPLICIT CHOICE {
      ueCapabilityInformation [0] UECapabilityInformation-IEs,
      criticalExtensionsFuture [1] SEQUENCE {

      }
   }
}

DRB-CountInfo ::= SEQUENCE {
   drb-Identity [0] DRB-Identity,
   count-Uplink [1] INTEGER (0..4294967295),
   count-Downlink [2] INTEGER (0..4294967295)
}

DRB-CountInfoList ::= SEQUENCE (SIZE (0..maxDRB)) OF DRB-CountInfo

CounterCheckResponse-IEs ::= SEQUENCE {
   drb-CountInfoList [0] DRB-CountInfoList,
   lateNonCriticalExtension [1] OCTET STRING OPTIONAL,
   nonCriticalExtension [2] SEQUENCE {

   } OPTIONAL
}

-- TAG-COUNTERCHECK-STOP
-- TAG-COUNTERCHECKRESPONSE-START
CounterCheckResponse ::= SEQUENCE {
   rrc-TransactionIdentifier [0] RRC-TransactionIdentifier,
   criticalExtensions [1] EXPLICIT CHOICE {
      counterCheckResponse [0] CounterCheckResponse-IEs,
      criticalExtensionsFuture [1] SEQUENCE {

      }
   }
}

DelayBudgetReport ::= CHOICE {
   type1 [0] ENUMERATED { msMinus1280(0), msMinus640(1), msMinus320(2), 
      msMinus160(3), msMinus80(4), msMinus60(5), msMinus40(6), msMinus20(7), 
      ms0(8), ms20(9), ms40(10), ms60(11), ms80(12), ms160(13), ms320(14), 
      ms640(15), ms1280(16) },
   ...
}

ReducedMaxCCs-r16 ::= SEQUENCE {
   reducedCCsDL-r16 [0] INTEGER (0..31),
   reducedCCsUL-r16 [1] INTEGER (0..31)
}

ReducedMaxBW-FRx-r16 ::= SEQUENCE {
   reducedBW-DL-r16 [0] ReducedAggregatedBandwidth,
   reducedBW-UL-r16 [1] ReducedAggregatedBandwidth
}

OverheatingAssistance ::= SEQUENCE {
   reducedMaxCCs [0] ReducedMaxCCs-r16 OPTIONAL,
   reducedMaxBW-FR1 [1] ReducedMaxBW-FRx-r16 OPTIONAL,
   reducedMaxBW-FR2 [2] ReducedMaxBW-FRx-r16 OPTIONAL,
   reducedMaxMIMO-LayersFR1 [3] SEQUENCE {
      reducedMIMO-LayersFR1-DL [0] MIMO-LayersDL,
      reducedMIMO-LayersFR1-UL [1] MIMO-LayersUL
   } OPTIONAL,
   reducedMaxMIMO-LayersFR2 [4] SEQUENCE {
      reducedMIMO-LayersFR2-DL [0] MIMO-LayersDL,
      reducedMIMO-LayersFR2-UL [1] MIMO-LayersUL
   } OPTIONAL
}

AffectedCarrierFreq-r16 ::= SEQUENCE {
   carrierFreq-r16 [0] ARFCN-ValueNR,
   interferenceDirection-r16 [1] ENUMERATED { nr(0), other(1), both(2), 
      spare(3) }
}

AffectedCarrierFreqList-r16 ::= SEQUENCE (SIZE (1..maxFreqIDC-r16)) OF AffectedCarrierFreq-r16
   

VictimSystemType-r16 ::= SEQUENCE {
   gps-r16 [0] ENUMERATED { true(0) } OPTIONAL,
   glonass-r16 [1] ENUMERATED { true(0) } OPTIONAL,
   bds-r16 [2] ENUMERATED { true(0) } OPTIONAL,
   galileo-r16 [3] ENUMERATED { true(0) } OPTIONAL,
   navIC-r16 [4] ENUMERATED { true(0) } OPTIONAL,
   wlan-r16 [5] ENUMERATED { true(0) } OPTIONAL,
   bluetooth-r16 [6] ENUMERATED { true(0) } OPTIONAL,
   ...
}

AffectedCarrierFreqComb-r16 ::= SEQUENCE {
   affectedCarrierFreqComb-r16 [0] SEQUENCE (SIZE (2..maxNrofServingCells)) OF ARFCN-ValueNR
       OPTIONAL,
   victimSystemType-r16 [1] VictimSystemType-r16
}

AffectedCarrierFreqCombList-r16 ::= SEQUENCE (SIZE (1..maxCombIDC-r16)) OF 
   AffectedCarrierFreqComb-r16

IDC-Assistance-r16 ::= SEQUENCE {
   affectedCarrierFreqList-r16 [0] AffectedCarrierFreqList-r16 OPTIONAL,
   affectedCarrierFreqCombList-r16 [1] AffectedCarrierFreqCombList-r16 OPTIONAL
      ,
   ...
}

DRX-Preference-r16 ::= SEQUENCE {
   preferredDRX-InactivityTimer-r16 [0] ENUMERATED { ms0(0), ms1(1), ms2(2), 
      ms3(3), ms4(4), ms5(5), ms6(6), ms8(7), ms10(8), ms20(9), ms30(10), 
      ms40(11), ms50(12), ms60(13), ms80(14), ms100(15), ms200(16), ms300(17), 
      ms500(18), ms750(19), ms1280(20), ms1920(21), ms2560(22), spare9(23), 
      spare8(24), spare7(25), spare6(26), spare5(27), spare4(28), spare3(29), 
      spare2(30), spare1(31) } OPTIONAL,
   preferredDRX-LongCycle-r16 [1] ENUMERATED { ms10(0), ms20(1), ms32(2), 
      ms40(3), ms60(4), ms64(5), ms70(6), ms80(7), ms128(8), ms160(9), 
      ms256(10), ms320(11), ms512(12), ms640(13), ms1024(14), ms1280(15), 
      ms2048(16), ms2560(17), ms5120(18), ms10240(19), spare12(20), spare11(21)
      , spare10(22), spare9(23), spare8(24), spare7(25), spare6(26), spare5(27)
      , spare4(28), spare3(29), spare2(30), spare1(31) } OPTIONAL,
   preferredDRX-ShortCycle-r16 [2] ENUMERATED { ms2(0), ms3(1), ms4(2), ms5(3)
      , ms6(4), ms7(5), ms8(6), ms10(7), ms14(8), ms16(9), ms20(10), ms30(11), 
      ms32(12), ms35(13), ms40(14), ms64(15), ms80(16), ms128(17), ms160(18), 
      ms256(19), ms320(20), ms512(21), ms640(22), spare9(23), spare8(24), 
      spare7(25), spare6(26), spare5(27), spare4(28), spare3(29), spare2(30), 
      spare1(31) } OPTIONAL,
   preferredDRX-ShortCycleTimer-r16 [3] INTEGER (1..16) OPTIONAL
}

MaxBW-Preference-r16 ::= SEQUENCE {
   reducedMaxBW-FR1-r16 [0] ReducedMaxBW-FRx-r16 OPTIONAL,
   reducedMaxBW-FR2-r16 [1] ReducedMaxBW-FRx-r16 OPTIONAL
}

MaxCC-Preference-r16 ::= SEQUENCE {
   reducedMaxCCs-r16 [0] ReducedMaxCCs-r16 OPTIONAL
}

MaxMIMO-LayerPreference-r16 ::= SEQUENCE {
   reducedMaxMIMO-LayersFR1-r16 [0] SEQUENCE {
      reducedMIMO-LayersFR1-DL-r16 [0] INTEGER (1..8),
      reducedMIMO-LayersFR1-UL-r16 [1] INTEGER (1..4)
   } OPTIONAL,
   reducedMaxMIMO-LayersFR2-r16 [1] SEQUENCE {
      reducedMIMO-LayersFR2-DL-r16 [0] INTEGER (1..8),
      reducedMIMO-LayersFR2-UL-r16 [1] INTEGER (1..4)
   } OPTIONAL
}

MinSchedulingOffsetPreference-r16 ::= SEQUENCE {
   preferredK0-r16 [0] SEQUENCE {
      preferredK0-SCS-15kHz-r16 [0] ENUMERATED { sl1(0), sl2(1), sl4(2), sl6(3)
          } OPTIONAL,
      preferredK0-SCS-30kHz-r16 [1] ENUMERATED { sl1(0), sl2(1), sl4(2), sl6(3)
          } OPTIONAL,
      preferredK0-SCS-60kHz-r16 [2] ENUMERATED { sl2(0), sl4(1), sl8(2), 
         sl12(3) } OPTIONAL,
      preferredK0-SCS-120kHz-r16 [3] ENUMERATED { sl2(0), sl4(1), sl8(2), 
         sl12(3) } OPTIONAL
   } OPTIONAL,
   preferredK2-r16 [1] SEQUENCE {
      preferredK2-SCS-15kHz-r16 [0] ENUMERATED { sl1(0), sl2(1), sl4(2), sl6(3)
          } OPTIONAL,
      preferredK2-SCS-30kHz-r16 [1] ENUMERATED { sl1(0), sl2(1), sl4(2), sl6(3)
          } OPTIONAL,
      preferredK2-SCS-60kHz-r16 [2] ENUMERATED { sl2(0), sl4(1), sl8(2), 
         sl12(3) } OPTIONAL,
      preferredK2-SCS-120kHz-r16 [3] ENUMERATED { sl2(0), sl4(1), sl8(2), 
         sl12(3) } OPTIONAL
   } OPTIONAL
}

ReleasePreference-r16 ::= SEQUENCE {
   preferredRRC-State-r16 [0] ENUMERATED { idle(0), inactive(1), connected(2), 
      outOfConnected(3) }
}

SL-TrafficPatternInfo-r16 ::= SEQUENCE {
   trafficPeriodicity-r16 [0] ENUMERATED { ms20(0), ms50(1), ms100(2), ms200(3)
      , ms300(4), ms400(5), ms500(6), ms600(7), ms700(8), ms800(9), ms900(10), 
      ms1000(11) },
   timingOffset-r16 [1] INTEGER (0..10239),
   messageSize-r16 [2] BIT STRING  (SIZE (8)),
   sl-QoS-FlowIdentity-r16 [3] SL-QoS-FlowIdentity-r16
}

SL-UE-AssistanceInformationNR-r16 ::= SEQUENCE (SIZE (1..maxNrofTrafficPattern-r16)) OF 
   SL-TrafficPatternInfo-r16

UL-GapFR2-Preference-r17 ::= SEQUENCE {
   ul-GapFR2-PatternPreference-r17 [0] INTEGER (0..3) OPTIONAL
}

MUSIM-GapPreferenceList-r17 ::= SEQUENCE (SIZE (1..4)) OF MUSIM-GapInfo-r17

MUSIM-Assistance-r17 ::= SEQUENCE {
   musim-PreferredRRC-State-r17 [0] ENUMERATED { idle(0), inactive(1), 
      outOfConnected(2) } OPTIONAL,
   musim-GapPreferenceList-r17 [1] MUSIM-GapPreferenceList-r17 OPTIONAL
}

OverheatingAssistance-r17 ::= SEQUENCE {
   reducedMaxBW-FR2-2-r17 [0] SEQUENCE {
      reducedBW-FR2-2-DL-r17 [0] ReducedAggregatedBandwidth-r17,
      reducedBW-FR2-2-UL-r17 [1] ReducedAggregatedBandwidth-r17
   } OPTIONAL,
   reducedMaxMIMO-LayersFR2-2 [1] SEQUENCE {
      reducedMIMO-LayersFR2-2-DL [0] MIMO-LayersDL,
      reducedMIMO-LayersFR2-2-UL [1] MIMO-LayersUL
   } OPTIONAL
}

MaxBW-PreferenceFR2-2-r17 ::= SEQUENCE {
   reducedMaxBW-FR2-2-r17 [0] SEQUENCE {
      reducedBW-FR2-2-DL-r17 [0] ReducedAggregatedBandwidth-r17 OPTIONAL,
      reducedBW-FR2-2-UL-r17 [1] ReducedAggregatedBandwidth-r17 OPTIONAL
   } OPTIONAL
}

MaxMIMO-LayerPreferenceFR2-2-r17 ::= SEQUENCE {
   reducedMaxMIMO-LayersFR2-2-r17 [0] SEQUENCE {
      reducedMIMO-LayersFR2-2-DL-r17 [0] INTEGER (1..8),
      reducedMIMO-LayersFR2-2-UL-r17 [1] INTEGER (1..4)
   } OPTIONAL
}

MinSchedulingOffsetPreferenceExt-r17 ::= SEQUENCE {
   preferredK0-r17 [0] SEQUENCE {
      preferredK0-SCS-480kHz-r17 [0] ENUMERATED { sl8(0), sl16(1), sl32(2), 
         sl48(3) } OPTIONAL,
      preferredK0-SCS-960kHz-r17 [1] ENUMERATED { sl8(0), sl16(1), sl32(2), 
         sl48(3) } OPTIONAL
   } OPTIONAL,
   preferredK2-r17 [1] SEQUENCE {
      preferredK2-SCS-480kHz-r17 [0] ENUMERATED { sl8(0), sl16(1), sl32(2), 
         sl48(3) } OPTIONAL,
      preferredK2-SCS-960kHz-r17 [1] ENUMERATED { sl8(0), sl16(1), sl32(2), 
         sl48(3) } OPTIONAL
   } OPTIONAL
}

PropagationDelayDifference-r17 ::= SEQUENCE (SIZE (1..4)) OF INTEGER (-270..270)

UEAssistanceInformation-v1700-IEs ::= SEQUENCE {
   ul-GapFR2-Preference-r17 [0] UL-GapFR2-Preference-r17 OPTIONAL,
   musim-Assistance-r17 [1] MUSIM-Assistance-r17 OPTIONAL,
   overheatingAssistance-r17 [2] OverheatingAssistance-r17 OPTIONAL,
   maxBW-PreferenceFR2-2-r17 [3] MaxBW-PreferenceFR2-2-r17 OPTIONAL,
   maxMIMO-LayerPreferenceFR2-2-r17 [4] MaxMIMO-LayerPreferenceFR2-2-r17
       OPTIONAL,
   minSchedulingOffsetPreferenceExt-r17 [5] 
      MinSchedulingOffsetPreferenceExt-r17 OPTIONAL,
   rlm-MeasRelaxationState-r17 [6] BOOLEAN OPTIONAL,
   bfd-MeasRelaxationState-r17 [7] BIT STRING  (SIZE (1..maxNrofServingCells)) OPTIONAL,
   nonSDT-DataIndication-r17 [8] SEQUENCE {
      resumeCause-r17 [0] ResumeCause OPTIONAL
   } OPTIONAL,
   scg-DeactivationPreference-r17 [9] ENUMERATED { scgDeactivationPreferred(0)
      , noPreference(1) } OPTIONAL,
   uplinkData-r17 [10] ENUMERATED { true(0) } OPTIONAL,
   rrm-MeasRelaxationFulfilment-r17 [11] BOOLEAN OPTIONAL,
   propagationDelayDifference-r17 [12] PropagationDelayDifference-r17 OPTIONAL,
   nonCriticalExtension [13] SEQUENCE {

   } OPTIONAL
}

UEAssistanceInformation-v1610-IEs ::= SEQUENCE {
   idc-Assistance-r16 [0] IDC-Assistance-r16 OPTIONAL,
   drx-Preference-r16 [1] DRX-Preference-r16 OPTIONAL,
   maxBW-Preference-r16 [2] MaxBW-Preference-r16 OPTIONAL,
   maxCC-Preference-r16 [3] MaxCC-Preference-r16 OPTIONAL,
   maxMIMO-LayerPreference-r16 [4] MaxMIMO-LayerPreference-r16 OPTIONAL,
   minSchedulingOffsetPreference-r16 [5] MinSchedulingOffsetPreference-r16
       OPTIONAL,
   releasePreference-r16 [6] ReleasePreference-r16 OPTIONAL,
   sl-UE-AssistanceInformationNR-r16 [7] SL-UE-AssistanceInformationNR-r16
       OPTIONAL,
   referenceTimeInfoPreference-r16 [8] BOOLEAN OPTIONAL,
   nonCriticalExtension [9] UEAssistanceInformation-v1700-IEs OPTIONAL
}

UEAssistanceInformation-v1540-IEs ::= SEQUENCE {
   overheatingAssistance [0] OverheatingAssistance OPTIONAL,
   nonCriticalExtension [1] UEAssistanceInformation-v1610-IEs OPTIONAL
}

UEAssistanceInformation-IEs ::= SEQUENCE {
   delayBudgetReport [0] EXPLICIT DelayBudgetReport OPTIONAL,
   lateNonCriticalExtension [1] OCTET STRING OPTIONAL,
   nonCriticalExtension [2] UEAssistanceInformation-v1540-IEs OPTIONAL
}

-- TAG-SYSTEMINFORMATION-STOP
-- TAG-UEASSISTANCEINFORMATION-START
UEAssistanceInformation ::= SEQUENCE {
   criticalExtensions [0] EXPLICIT CHOICE {
      ueAssistanceInformation [0] UEAssistanceInformation-IEs,
      criticalExtensionsFuture [1] SEQUENCE {

      }
   }
}

FailureInfoRLC-Bearer ::= SEQUENCE {
   cellGroupId [0] CellGroupId,
   logicalChannelIdentity [1] LogicalChannelIdentity,
   failureType [2] ENUMERATED { rlc-failure(0), spare3(1), spare2(2), spare1(3)
       }
}

FailureInfoDAPS-r16 ::= SEQUENCE {
   failureType-r16 [0] ENUMERATED { daps-failure(0), spare3(1), spare2(2), 
      spare1(3) }
}

FailureInformation-v1610-IEs ::= SEQUENCE {
   failureInfoDAPS-r16 [0] FailureInfoDAPS-r16 OPTIONAL,
   nonCriticalExtension [1] SEQUENCE {

   } OPTIONAL
}

FailureInformation-IEs ::= SEQUENCE {
   failureInfoRLC-Bearer [0] FailureInfoRLC-Bearer OPTIONAL,
   lateNonCriticalExtension [1] OCTET STRING OPTIONAL,
   nonCriticalExtension [2] FailureInformation-v1610-IEs OPTIONAL
}

-- TAG-DLINFORMATIONTRANSFERMRDC-STOP
-- TAG-FAILUREINFORMATION-START
FailureInformation ::= SEQUENCE {
   criticalExtensions [0] EXPLICIT CHOICE {
      failureInformation [0] FailureInformation-IEs,
      criticalExtensionsFuture [1] SEQUENCE {

      }
   }
}

ULInformationTransferMRDC-IEs ::= SEQUENCE {
   ul-DCCH-MessageNR [0] OCTET STRING OPTIONAL,
   ul-DCCH-MessageEUTRA [1] OCTET STRING OPTIONAL,
   lateNonCriticalExtension [2] OCTET STRING OPTIONAL,
   nonCriticalExtension [3] SEQUENCE {

   } OPTIONAL
}

-- TAG-ULINFORMATIONTRANSFERIRAT-STOP
-- TAG-ULINFORMATIONTRANSFERMRDC-START
ULInformationTransferMRDC ::= SEQUENCE {
   criticalExtensions [0] EXPLICIT CHOICE {
      c1 [0] EXPLICIT CHOICE {
         ulInformationTransferMRDC [0] ULInformationTransferMRDC-IEs,
         spare3 [1] NULL,
         spare2 [2] NULL,
         spare1 [3] NULL
      },
      criticalExtensionsFuture [1] SEQUENCE {

      }
   }
}

MeasResultFreqList ::= SEQUENCE (SIZE (1..maxFreq)) OF MeasResult2NR

MeasResultList2NR ::= SEQUENCE (SIZE (1..maxFreq)) OF MeasResult2NR

-- TAG-MEASRESULTRXTXTIMEDIFF-STOP
-- TAG-MEASRESULTSCG-FAILURE-START
MeasResultSCG-Failure ::= SEQUENCE {
   measResultPerMOList [0] MeasResultList2NR,
   ...,
   [[
      locationInfo-r16 [1] LocationInfo-r16 OPTIONAL
   ]]
}

PerRAAttemptInfo-r16 ::= SEQUENCE {
   contentionDetected-r16 [0] BOOLEAN OPTIONAL,
   dlRSRPAboveThreshold-r16 [1] BOOLEAN OPTIONAL,
   ...,
   [[
      fallbackToFourStepRA-r17 [2] ENUMERATED { true(0) } OPTIONAL
   ]]
}

PerRAAttemptInfoList-r16 ::= SEQUENCE (SIZE (1..200)) OF PerRAAttemptInfo-r16

PerRASSBInfo-r16 ::= SEQUENCE {
   ssb-Index-r16 [0] SSB-Index,
   numberOfPreamblesSentOnSSB-r16 [1] INTEGER (1..200),
   perRAAttemptInfoList-r16 [2] PerRAAttemptInfoList-r16
}

PerRACSI-RSInfo-r16 ::= SEQUENCE {
   csi-RS-Index-r16 [0] CSI-RS-Index,
   numberOfPreamblesSentOnCSI-RS-r16 [1] INTEGER (1..200)
}

PerRAInfo-r16 ::= CHOICE {
   perRASSBInfoList-r16 [0] PerRASSBInfo-r16,
   perRACSI-RSInfoList-r16 [1] PerRACSI-RSInfo-r16
}

PerRAInfoList-r16 ::= SEQUENCE (SIZE (1..200)) OF PerRAInfo-r16

FailureReportSCG ::= SEQUENCE {
   failureType [0] ENUMERATED { t310-Expiry(0), randomAccessProblem(1), 
      rlc-MaxNumRetx(2), synchReconfigFailureSCG(3), scg-ReconfigFailure(4), 
      srb3-IntegrityFailure(5), other-r16(6), spare1(7) },
   measResultFreqList [1] MeasResultFreqList OPTIONAL,
   measResultSCG-Failure [2] OCTET STRING (CONTAINING MeasResultSCG-Failure)
       OPTIONAL,
   ...,
   [[
      locationInfo-r16 [3] LocationInfo-r16 OPTIONAL,
      failureType-v1610 [4] ENUMERATED { scg-lbtFailure-r16(0), 
         beamFailureRecoveryFailure-r16(1), t312-Expiry-r16(2), bh-RLF-r16(3), 
         beamFailure-r17(4), spare3(5), spare2(6), spare1(7) } OPTIONAL
   ]],
   [[
      previousPSCellId-r17 [5] SEQUENCE {
         physCellId-r17 [0] PhysCellId,
         carrierFreq-r17 [1] ARFCN-ValueNR
      } OPTIONAL,
      failedPSCellId-r17 [6] SEQUENCE {
         physCellId-r17 [0] PhysCellId,
         carrierFreq-r17 [1] ARFCN-ValueNR
      } OPTIONAL,
      timeSCGFailure-r17 [7] INTEGER (0..1023) OPTIONAL,
      perRAInfoList-r17 [8] PerRAInfoList-r16 OPTIONAL
   ]]
}

SCGFailureInformation-v1590-IEs ::= SEQUENCE {
   lateNonCriticalExtension [0] OCTET STRING OPTIONAL,
   nonCriticalExtension [1] SEQUENCE {

   } OPTIONAL
}

SCGFailureInformation-IEs ::= SEQUENCE {
   failureReportSCG [0] FailureReportSCG OPTIONAL,
   nonCriticalExtension [1] SCGFailureInformation-v1590-IEs OPTIONAL
}

-- TAG-RRCSYSTEMINFOREQUEST-STOP
-- TAG-SCGFAILUREINFORMATION-START
SCGFailureInformation ::= SEQUENCE {
   criticalExtensions [0] EXPLICIT CHOICE {
      scgFailureInformation [0] SCGFailureInformation-IEs,
      criticalExtensionsFuture [1] SEQUENCE {

      }
   }
}

MeasResultFreqListFailMRDC ::= SEQUENCE (SIZE (1..maxFreq)) OF MeasResult2EUTRA

FailureReportSCG-EUTRA ::= SEQUENCE {
   failureType [0] ENUMERATED { t313-Expiry(0), randomAccessProblem(1), 
      rlc-MaxNumRetx(2), scg-ChangeFailure(3), spare4(4), spare3(5), spare2(6)
      , spare1(7) },
   measResultFreqListMRDC [1] MeasResultFreqListFailMRDC OPTIONAL,
   measResultSCG-FailureMRDC [2] OCTET STRING OPTIONAL,
   ...,
   [[
      locationInfo-r16 [3] LocationInfo-r16 OPTIONAL
   ]]
}

SCGFailureInformationEUTRA-v1590-IEs ::= SEQUENCE {
   lateNonCriticalExtension [0] OCTET STRING OPTIONAL,
   nonCriticalExtension [1] SEQUENCE {

   } OPTIONAL
}

SCGFailureInformationEUTRA-IEs ::= SEQUENCE {
   failureReportSCG-EUTRA [0] FailureReportSCG-EUTRA OPTIONAL,
   nonCriticalExtension [1] SCGFailureInformationEUTRA-v1590-IEs OPTIONAL
}

-- TAG-SCGFAILUREINFORMATION-STOP
-- TAG-SCGFAILUREINFORMATIONEUTRA-START
SCGFailureInformationEUTRA ::= SEQUENCE {
   criticalExtensions [0] EXPLICIT CHOICE {
      scgFailureInformationEUTRA [0] SCGFailureInformationEUTRA-IEs,
      criticalExtensionsFuture [1] SEQUENCE {

      }
   }
}

ULDedicatedMessageSegment-r16-IEs ::= SEQUENCE {
   segmentNumber-r16 [0] INTEGER (0..15),
   rrc-MessageSegmentContainer-r16 [1] OCTET STRING,
   rrc-MessageSegmentType-r16 [2] ENUMERATED { notLastSegment(0), 
      lastSegment(1) },
   lateNonCriticalExtension [3] OCTET STRING OPTIONAL,
   nonCriticalExtension [4] SEQUENCE {

   } OPTIONAL
}

-- TAG-UEPOSITIONINGASSISTANCEINFO-STOP
-- TAG-ULDEDICATEDMESSAGESEGMENT-START
ULDedicatedMessageSegment-r16 ::= SEQUENCE {
   criticalExtensions [0] EXPLICIT CHOICE {
      ulDedicatedMessageSegment-r16 [0] ULDedicatedMessageSegment-r16-IEs,
      criticalExtensionsFuture [1] SEQUENCE {

      }
   }
}

PosSIB-ReqInfo-r16 ::= SEQUENCE {
   gnss-id-r16 [0] GNSS-ID-r16 OPTIONAL,
   sbas-id-r16 [1] SBAS-ID-r16 OPTIONAL,
   posSibType-r16 [2] ENUMERATED { posSibType1-1(0), posSibType1-2(1), 
      posSibType1-3(2), posSibType1-4(3), posSibType1-5(4), posSibType1-6(5), 
      posSibType1-7(6), posSibType1-8(7), posSibType2-1(8), posSibType2-2(9), 
      posSibType2-3(10), posSibType2-4(11), posSibType2-5(12), 
      posSibType2-6(13), posSibType2-7(14), posSibType2-8(15), 
      posSibType2-9(16), posSibType2-10(17), posSibType2-11(18), 
      posSibType2-12(19), posSibType2-13(20), posSibType2-14(21), 
      posSibType2-15(22), posSibType2-16(23), posSibType2-17(24), 
      posSibType2-18(25), posSibType2-19(26), posSibType2-20(27), 
      posSibType2-21(28), posSibType2-22(29), posSibType2-23(30), 
      posSibType3-1(31), posSibType4-1(32), posSibType5-1(33), 
      posSibType6-1(34), posSibType6-2(35), posSibType6-3(36), ..., 
      posSibType1-9-v1710(37), posSibType1-10-v1710(38), 
      posSibType2-24-v1710(39), posSibType2-25-v1710(40), 
      posSibType6-4-v1710(41), posSibType6-5-v1710(42), posSibType6-6-v1710(43)
      , posSibType2-17a-v1770(44), posSibType2-18a-v1770(45), 
      posSibType2-20a-v1770(46) }
}

DedicatedSIBRequest-r16-IEs ::= SEQUENCE {
   onDemandSIB-RequestList-r16 [0] SEQUENCE {
      requestedSIB-List-r16 [0] SEQUENCE (SIZE (1..maxOnDemandSIB-r16)) OF SIB-ReqInfo-r16
          OPTIONAL,
      requestedPosSIB-List-r16 [1] SEQUENCE (SIZE (1..maxOnDemandPosSIB-r16)) OF PosSIB-ReqInfo-r16
          OPTIONAL
   } OPTIONAL,
   lateNonCriticalExtension [1] OCTET STRING OPTIONAL,
   nonCriticalExtension [2] SEQUENCE {

   } OPTIONAL
}

-- TAG-COUNTERCHECKRESPONSE-STOP
-- TAG-DEDICATEDSIBREQUEST-START
DedicatedSIBRequest-r16 ::= SEQUENCE {
   criticalExtensions [0] EXPLICIT CHOICE {
      dedicatedSIBRequest-r16 [0] DedicatedSIBRequest-r16-IEs,
      criticalExtensionsFuture [1] SEQUENCE {

      }
   }
}

MeasResult2EUTRA-r16 ::= SEQUENCE {
   carrierFreq-r16 [0] ARFCN-ValueEUTRA,
   measResultList-r16 [1] MeasResultListEUTRA
}

MeasResultList2EUTRA ::= SEQUENCE (SIZE (1..maxFreq)) OF MeasResult2EUTRA-r16

MeasResult2UTRA-FDD-r16 ::= SEQUENCE {
   carrierFreq-r16 [0] ARFCN-ValueUTRA-FDD-r16,
   measResultNeighCellList-r16 [1] MeasResultListUTRA-FDD-r16
}

MeasResultList2UTRA ::= SEQUENCE (SIZE (1..maxFreq)) OF MeasResult2UTRA-FDD-r16

FailureReportMCG-r16 ::= SEQUENCE {
   failureType-r16 [0] ENUMERATED { t310-Expiry(0), randomAccessProblem(1), 
      rlc-MaxNumRetx(2), t312-Expiry-r16(3), lbt-Failure-r16(4), 
      beamFailureRecoveryFailure-r16(5), bh-RLF-r16(6), spare1(7) } OPTIONAL,
   measResultFreqList-r16 [1] MeasResultList2NR OPTIONAL,
   measResultFreqListEUTRA-r16 [2] MeasResultList2EUTRA OPTIONAL,
   measResultSCG-r16 [3] OCTET STRING (CONTAINING MeasResultSCG-Failure)
       OPTIONAL,
   measResultSCG-EUTRA-r16 [4] OCTET STRING OPTIONAL,
   measResultFreqListUTRA-FDD-r16 [5] MeasResultList2UTRA OPTIONAL,
   ...
}

MCGFailureInformation-r16-IEs ::= SEQUENCE {
   failureReportMCG-r16 [0] FailureReportMCG-r16 OPTIONAL,
   lateNonCriticalExtension [1] OCTET STRING OPTIONAL,
   nonCriticalExtension [2] SEQUENCE {

   } OPTIONAL
}

-- TAG-MBSINTERESTINDICATION-STOP
-- TAG-MCGFAILUREINFORMATION-START
MCGFailureInformation-r16 ::= SEQUENCE {
   criticalExtensions [0] EXPLICIT CHOICE {
      mcgFailureInformation-r16 [0] MCGFailureInformation-r16-IEs,
      criticalExtensionsFuture [1] SEQUENCE {

      }
   }
}

MeasResultServingCell-r16 ::= SEQUENCE {
   resultsSSB-Cell [0] MeasQuantityResults,
   resultsSSB [1] SEQUENCE {
      best-ssb-Index [0] SSB-Index,
      best-ssb-Results [1] MeasQuantityResults,
      numberOfGoodSSB [2] INTEGER (1..maxNrofSSBs-r16)
   } OPTIONAL
}

MeasResultLoggingNR-r16 ::= SEQUENCE {
   physCellId-r16 [0] PhysCellId,
   resultsSSB-Cell-r16 [1] MeasQuantityResults,
   numberOfGoodSSB-r16 [2] INTEGER (1..maxNrofSSBs-r16) OPTIONAL
}

MeasResultListLoggingNR-r16 ::= SEQUENCE (SIZE (1..maxCellReport)) OF MeasResultLoggingNR-r16
   

MeasResultLogging2NR-r16 ::= SEQUENCE {
   carrierFreq-r16 [0] ARFCN-ValueNR,
   measResultListLoggingNR-r16 [1] MeasResultListLoggingNR-r16
}

MeasResultListLogging2NR-r16 ::= SEQUENCE (SIZE (1..maxFreq)) OF 
   MeasResultLogging2NR-r16

MeasResultList2EUTRA-r16 ::= SEQUENCE (SIZE (1..maxFreq)) OF MeasResult2EUTRA-r16

LogMeasInfo-r16 ::= SEQUENCE {
   locationInfo-r16 [0] LocationInfo-r16 OPTIONAL,
   relativeTimeStamp-r16 [1] INTEGER (0..7200),
   servCellIdentity-r16 [2] CGI-Info-Logging-r16 OPTIONAL,
   measResultServingCell-r16 [3] MeasResultServingCell-r16 OPTIONAL,
   measResultNeighCells-r16 [4] SEQUENCE {
      measResultNeighCellListNR [0] MeasResultListLogging2NR-r16 OPTIONAL,
      measResultNeighCellListEUTRA [1] MeasResultList2EUTRA-r16 OPTIONAL
   },
   anyCellSelectionDetected-r16 [5] ENUMERATED { true(0) } OPTIONAL,
   ...,
   [[
      inDeviceCoexDetected-r17 [6] ENUMERATED { true(0) } OPTIONAL
   ]]
}

LogMeasInfoList-r16 ::= SEQUENCE (SIZE (1..maxLogMeasReport-r16)) OF LogMeasInfo-r16

LogMeasReport-r16 ::= SEQUENCE {
   absoluteTimeStamp-r16 [0] AbsoluteTimeInfo-r16,
   traceReference-r16 [1] TraceReference-r16,
   traceRecordingSessionRef-r16 [2] OCTET STRING (SIZE (2)),
   tce-Id-r16 [3] OCTET STRING (SIZE (1)),
   logMeasInfoList-r16 [4] LogMeasInfoList-r16,
   logMeasAvailable-r16 [5] ENUMERATED { true(0) } OPTIONAL,
   logMeasAvailableBT-r16 [6] ENUMERATED { true(0) } OPTIONAL,
   logMeasAvailableWLAN-r16 [7] ENUMERATED { true(0) } OPTIONAL,
   ...
}

MeasResultFailedCell-r16 ::= SEQUENCE {
   cgi-Info [0] CGI-Info-Logging-r16,
   measResult-r16 [1] SEQUENCE {
      cellResults-r16 [0] SEQUENCE {
         resultsSSB-Cell-r16 [0] MeasQuantityResults
      },
      rsIndexResults-r16 [1] SEQUENCE {
         resultsSSB-Indexes-r16 [0] ResultsPerSSB-IndexList
      }
   }
}

MeasResult2NR-r16 ::= SEQUENCE {
   ssbFrequency-r16 [0] ARFCN-ValueNR OPTIONAL,
   refFreqCSI-RS-r16 [1] ARFCN-ValueNR OPTIONAL,
   measResultList-r16 [2] MeasResultListNR
}

MeasResultList2NR-r16 ::= SEQUENCE (SIZE (1..maxFreq)) OF MeasResult2NR-r16

ConnEstFailReport-r16 ::= SEQUENCE {
   measResultFailedCell-r16 [0] MeasResultFailedCell-r16,
   locationInfo-r16 [1] LocationInfo-r16 OPTIONAL,
   measResultNeighCells-r16 [2] SEQUENCE {
      measResultNeighCellListNR [0] MeasResultList2NR-r16 OPTIONAL,
      measResultNeighCellListEUTRA [1] MeasResultList2EUTRA-r16 OPTIONAL
   },
   numberOfConnFail-r16 [3] INTEGER (1..8),
   perRAInfoList-r16 [4] PerRAInfoList-r16,
   timeSinceFailure-r16 [5] TimeSinceFailure-r16,
   ...
}

PerRACSI-RSInfo-v1660 ::= SEQUENCE {
   csi-RS-Index-v1660 [0] INTEGER (1..96) OPTIONAL
}

PerRAInfoList-v1660 ::= SEQUENCE (SIZE (1..200)) OF PerRACSI-RSInfo-v1660

RA-InformationCommon-r16 ::= SEQUENCE {
   absoluteFrequencyPointA-r16 [0] ARFCN-ValueNR,
   locationAndBandwidth-r16 [1] INTEGER (0..37949),
   subcarrierSpacing-r16 [2] SubcarrierSpacing,
   msg1-FrequencyStart-r16 [3] INTEGER (0..maxNrofPhysicalResourceBlocks-1) OPTIONAL,
   msg1-FrequencyStartCFRA-r16 [4] INTEGER (0..maxNrofPhysicalResourceBlocks-1) OPTIONAL,
   msg1-SubcarrierSpacing-r16 [5] SubcarrierSpacing OPTIONAL,
   msg1-SubcarrierSpacingCFRA-r16 [6] SubcarrierSpacing OPTIONAL,
   msg1-FDM-r16 [7] ENUMERATED { one(0), two(1), four(2), eight(3) } OPTIONAL,
   msg1-FDMCFRA-r16 [8] ENUMERATED { one(0), two(1), four(2), eight(3) }
       OPTIONAL,
   perRAInfoList-r16 [9] PerRAInfoList-r16,
   ...,
   [[
      perRAInfoList-v1660 [10] PerRAInfoList-v1660 OPTIONAL
   ]],
   [[
      msg1-SCS-From-prach-ConfigurationIndex-r16 [11] ENUMERATED { kHz1dot25(0)
         , kHz5(1), spare2(2), spare1(3) } OPTIONAL
   ]],
   [[
      msg1-SCS-From-prach-ConfigurationIndexCFRA-r16 [12] ENUMERATED { 
         kHz1dot25(0), kHz5(1), spare2(2), spare1(3) } OPTIONAL
   ]],
   [[
      msgA-RO-FrequencyStart-r17 [13] INTEGER (0..maxNrofPhysicalResourceBlocks-1) OPTIONAL,
      msgA-RO-FrequencyStartCFRA-r17 [14] INTEGER (0..maxNrofPhysicalResourceBlocks-1) OPTIONAL,
      msgA-SubcarrierSpacing-r17 [15] SubcarrierSpacing OPTIONAL,
      msgA-RO-FDM-r17 [16] ENUMERATED { one(0), two(1), four(2), eight(3) }
          OPTIONAL,
      msgA-RO-FDMCFRA-r17 [17] ENUMERATED { one(0), two(1), four(2), eight(3) }
          OPTIONAL,
      msgA-SCS-From-prach-ConfigurationIndex-r17 [18] ENUMERATED { kHz1dot25(0)
         , kHz5(1), spare2(2), spare1(3) } OPTIONAL,
      msgA-TransMax-r17 [19] ENUMERATED { n1(0), n2(1), n4(2), n6(3), n8(4), 
         n10(5), n20(6), n50(7), n100(8), n200(9) } OPTIONAL,
      msgA-MCS-r17 [20] INTEGER (0..15) OPTIONAL,
      nrofPRBs-PerMsgA-PO-r17 [21] INTEGER (1..32) OPTIONAL,
      msgA-PUSCH-TimeDomainAllocation-r17 [22] INTEGER (1..maxNrofUL-Allocations) OPTIONAL,
      frequencyStartMsgA-PUSCH-r17 [23] INTEGER (0..maxNrofPhysicalResourceBlocks-1) OPTIONAL,
      nrofMsgA-PO-FDM-r17 [24] ENUMERATED { one(0), two(1), four(2), eight(3) }
          OPTIONAL,
      dlPathlossRSRP-r17 [25] RSRP-Range OPTIONAL,
      intendedSIBs-r17 [26] SEQUENCE (SIZE (1..maxSIB)) OF SIB-Type-r17 OPTIONAL,
      ssbsForSI-Acquisition-r17 [27] SEQUENCE (SIZE (1..maxNrofSSBs-r16)) OF SSB-Index OPTIONAL
         ,
      msgA-PUSCH-PayloadSize-r17 [28] BIT STRING  (SIZE (5)) OPTIONAL,
      onDemandSISuccess-r17 [29] ENUMERATED { true(0) } OPTIONAL
   ]]
}

RA-Report-r16 ::= SEQUENCE {
   cellId-r16 [0] EXPLICIT CHOICE {
      cellGlobalId-r16 [0] CGI-Info-Logging-r16,
      pci-arfcn-r16 [1] PCI-ARFCN-NR-r16
   },
   ra-InformationCommon-r16 [1] RA-InformationCommon-r16 OPTIONAL,
   raPurpose-r16 [2] ENUMERATED { accessRelated(0), beamFailureRecovery(1), 
      reconfigurationWithSync(2), ulUnSynchronized(3), 
      schedulingRequestFailure(4), noPUCCHResourceAvailable(5), 
      requestForOtherSI(6), msg3RequestForOtherSI-r17(7), spare8(8), spare7(9)
      , spare6(10), spare5(11), spare4(12), spare3(13), spare2(14), spare1(15)
       },
   ...,
   [[
      spCellID-r17 [3] CGI-Info-Logging-r16 OPTIONAL
   ]]
}

RA-ReportList-r16 ::= SEQUENCE (SIZE (1..maxRAReport-r16)) OF RA-Report-r16

MeasResultRLFNR-r16 ::= SEQUENCE {
   measResult-r16 [0] SEQUENCE {
      cellResults-r16 [0] SEQUENCE {
         resultsSSB-Cell-r16 [0] MeasQuantityResults OPTIONAL,
         resultsCSI-RS-Cell-r16 [1] MeasQuantityResults OPTIONAL
      },
      rsIndexResults-r16 [1] SEQUENCE {
         resultsSSB-Indexes-r16 [0] ResultsPerSSB-IndexList OPTIONAL,
         ssbRLMConfigBitmap-r16 [1] BIT STRING  (SIZE (64)) OPTIONAL,
         resultsCSI-RS-Indexes-r16 [2] ResultsPerCSI-RS-IndexList OPTIONAL,
         csi-rsRLMConfigBitmap-r16 [3] BIT STRING  (SIZE (96)) OPTIONAL
      } OPTIONAL
   }
}

ChoCandidateCell-r17 ::= CHOICE {
   cellGlobalId-r17 [0] CGI-Info-Logging-r16,
   pci-arfcn-r17 [1] PCI-ARFCN-NR-r16
}

ChoCandidateCellList-r17 ::= SEQUENCE (SIZE (1..maxNrofCondCells-r16)) OF ChoCandidateCell-r17

RLF-Report-r16 ::= CHOICE {
   nr-RLF-Report-r16 [0] SEQUENCE {
      measResultLastServCell-r16 [0] MeasResultRLFNR-r16,
      measResultNeighCells-r16 [1] SEQUENCE {
         measResultListNR-r16 [0] MeasResultList2NR-r16 OPTIONAL,
         measResultListEUTRA-r16 [1] MeasResultList2EUTRA-r16 OPTIONAL
      } OPTIONAL,
      c-RNTI-r16 [2] RNTI-Value,
      previousPCellId-r16 [3] EXPLICIT CHOICE {
         nrPreviousCell-r16 [0] CGI-Info-Logging-r16,
         eutraPreviousCell-r16 [1] CGI-InfoEUTRALogging
      } OPTIONAL,
      failedPCellId-r16 [4] EXPLICIT CHOICE {
         nrFailedPCellId-r16 [0] EXPLICIT CHOICE {
            cellGlobalId-r16 [0] CGI-Info-Logging-r16,
            pci-arfcn-r16 [1] PCI-ARFCN-NR-r16
         },
         eutraFailedPCellId-r16 [1] EXPLICIT CHOICE {
            cellGlobalId-r16 [0] CGI-InfoEUTRALogging,
            pci-arfcn-r16 [1] PCI-ARFCN-EUTRA-r16
         }
      },
      reconnectCellId-r16 [5] EXPLICIT CHOICE {
         nrReconnectCellId-r16 [0] CGI-Info-Logging-r16,
         eutraReconnectCellId-r16 [1] CGI-InfoEUTRALogging
      } OPTIONAL,
      timeUntilReconnection-r16 [6] TimeUntilReconnection-r16 OPTIONAL,
      reestablishmentCellId-r16 [7] CGI-Info-Logging-r16 OPTIONAL,
      timeConnFailure-r16 [8] INTEGER (0..1023) OPTIONAL,
      timeSinceFailure-r16 [9] TimeSinceFailure-r16,
      connectionFailureType-r16 [10] ENUMERATED { rlf(0), hof(1) },
      rlf-Cause-r16 [11] ENUMERATED { t310-Expiry(0), randomAccessProblem(1), 
         rlc-MaxNumRetx(2), beamFailureRecoveryFailure(3), lbtFailure-r16(4), 
         bh-rlfRecoveryFailure(5), t312-expiry-r17(6), spare1(7) },
      locationInfo-r16 [12] LocationInfo-r16 OPTIONAL,
      noSuitableCellFound-r16 [13] ENUMERATED { true(0) } OPTIONAL,
      ra-InformationCommon-r16 [14] RA-InformationCommon-r16 OPTIONAL,
      ...,
      [[
         csi-rsRLMConfigBitmap-v1650 [15] BIT STRING  (SIZE (96)) OPTIONAL
      ]],
      [[
         lastHO-Type-r17 [16] ENUMERATED { cho(0), daps(1), spare2(2), 
            spare1(3) } OPTIONAL,
         timeConnSourceDAPS-Failure-r17 [17] TimeConnSourceDAPS-Failure-r17
             OPTIONAL,
         timeSinceCHO-Reconfig-r17 [18] TimeSinceCHO-Reconfig-r17 OPTIONAL,
         choCellId-r17 [19] EXPLICIT CHOICE {
            cellGlobalId-r17 [0] CGI-Info-Logging-r16,
            pci-arfcn-r17 [1] PCI-ARFCN-NR-r16
         } OPTIONAL,
         choCandidateCellList-r17 [20] ChoCandidateCellList-r17 OPTIONAL
      ]]
   },
   eutra-RLF-Report-r16 [1] SEQUENCE {
      failedPCellId-EUTRA [0] CGI-InfoEUTRALogging,
      measResult-RLF-Report-EUTRA-r16 [1] OCTET STRING,
      ...,
      [[
         measResult-RLF-Report-EUTRA-v1690 [2] OCTET STRING OPTIONAL
      ]]
   }
}

MeasResultSuccessHONR-r17 ::= SEQUENCE {
   measResult-r17 [0] SEQUENCE {
      cellResults-r17 [0] SEQUENCE {
         resultsSSB-Cell-r17 [0] MeasQuantityResults OPTIONAL,
         resultsCSI-RS-Cell-r17 [1] MeasQuantityResults OPTIONAL
      },
      rsIndexResults-r17 [1] SEQUENCE {
         resultsSSB-Indexes-r17 [0] ResultsPerSSB-IndexList OPTIONAL,
         resultsCSI-RS-Indexes-r17 [1] ResultsPerCSI-RS-IndexList OPTIONAL
      }
   }
}

SHR-Cause-r17 ::= SEQUENCE {
   t304-cause-r17 [0] ENUMERATED { true(0) } OPTIONAL,
   t310-cause-r17 [1] ENUMERATED { true(0) } OPTIONAL,
   t312-cause-r17 [2] ENUMERATED { true(0) } OPTIONAL,
   sourceDAPS-Failure-r17 [3] ENUMERATED { true(0) } OPTIONAL,
   ...
}

SuccessHO-Report-r17 ::= SEQUENCE {
   sourceCellInfo-r17 [0] SEQUENCE {
      sourcePCellId-r17 [0] CGI-Info-Logging-r16,
      sourceCellMeas-r17 [1] MeasResultSuccessHONR-r17 OPTIONAL,
      rlf-InSourceDAPS-r17 [2] ENUMERATED { true(0) } OPTIONAL
   },
   targetCellInfo-r17 [1] SEQUENCE {
      targetPCellId-r17 [0] CGI-Info-Logging-r16,
      targetCellMeas-r17 [1] MeasResultSuccessHONR-r17 OPTIONAL
   },
   measResultNeighCells-r17 [2] SEQUENCE {
      measResultListNR-r17 [0] MeasResultList2NR-r16 OPTIONAL,
      measResultListEUTRA-r17 [1] MeasResultList2EUTRA-r16 OPTIONAL
   } OPTIONAL,
   locationInfo-r17 [3] LocationInfo-r16 OPTIONAL,
   timeSinceCHO-Reconfig-r17 [4] TimeSinceCHO-Reconfig-r17 OPTIONAL,
   shr-Cause-r17 [5] SHR-Cause-r17 OPTIONAL,
   ra-InformationCommon-r17 [6] RA-InformationCommon-r16 OPTIONAL,
   upInterruptionTimeAtHO-r17 [7] UPInterruptionTimeAtHO-r17 OPTIONAL,
   c-RNTI-r17 [8] RNTI-Value OPTIONAL,
   ...
}

ConnEstFailReportList-r17 ::= SEQUENCE (SIZE (1..maxCEFReport-r17)) OF ConnEstFailReport-r16

UEInformationResponse-v1700-IEs ::= SEQUENCE {
   successHO-Report-r17 [0] SuccessHO-Report-r17 OPTIONAL,
   connEstFailReportList-r17 [1] ConnEstFailReportList-r17 OPTIONAL,
   coarseLocationInfo-r17 [2] OCTET STRING OPTIONAL,
   nonCriticalExtension [3] SEQUENCE {

   } OPTIONAL
}

UEInformationResponse-r16-IEs ::= SEQUENCE {
   measResultIdleEUTRA-r16 [0] MeasResultIdleEUTRA-r16 OPTIONAL,
   measResultIdleNR-r16 [1] MeasResultIdleNR-r16 OPTIONAL,
   logMeasReport-r16 [2] LogMeasReport-r16 OPTIONAL,
   connEstFailReport-r16 [3] ConnEstFailReport-r16 OPTIONAL,
   ra-ReportList-r16 [4] RA-ReportList-r16 OPTIONAL,
   rlf-Report-r16 [5] EXPLICIT RLF-Report-r16 OPTIONAL,
   mobilityHistoryReport-r16 [6] MobilityHistoryReport-r16 OPTIONAL,
   lateNonCriticalExtension [7] OCTET STRING OPTIONAL,
   nonCriticalExtension [8] UEInformationResponse-v1700-IEs OPTIONAL
}

-- TAG-UEINFORMATIONREQUEST-STOP
-- TAG-UEINFORMATIONRESPONSE-START
UEInformationResponse-r16 ::= SEQUENCE {
   rrc-TransactionIdentifier [0] RRC-TransactionIdentifier,
   criticalExtensions [1] EXPLICIT CHOICE {
      ueInformationResponse-r16 [0] UEInformationResponse-r16-IEs,
      criticalExtensionsFuture [1] SEQUENCE {

      }
   }
}

SL-InterestedFreqList-r16 ::= SEQUENCE (SIZE (1..maxNrofFreqSL-r16)) OF INTEGER (1..maxNrofFreqSL-r16)

SL-QoS-Info-r16 ::= SEQUENCE {
   sl-QoS-FlowIdentity-r16 [0] SL-QoS-FlowIdentity-r16,
   sl-QoS-Profile-r16 [1] SL-QoS-Profile-r16 OPTIONAL
}

SL-RLC-ModeIndication-r16 ::= SEQUENCE {
   sl-Mode-r16 [0] EXPLICIT CHOICE {
      sl-AM-Mode-r16 [0] NULL,
      sl-UM-Mode-r16 [1] NULL
   },
   sl-QoS-InfoList-r16 [1] SEQUENCE (SIZE (1..maxNrofSL-QFIsPerDest-r16)) OF SL-QoS-Info-r16
}

SL-TxInterestedFreqList-r16 ::= SEQUENCE (SIZE (1..maxNrofFreqSL-r16)) OF INTEGER (1..maxNrofFreqSL-r16)

SL-TxResourceReq-r16 ::= SEQUENCE {
   sl-DestinationIdentity-r16 [0] SL-DestinationIdentity-r16,
   sl-CastType-r16 [1] ENUMERATED { broadcast(0), groupcast(1), unicast(2), 
      spare1(3) },
   sl-RLC-ModeIndicationList-r16 [2] SEQUENCE (SIZE (1..maxNrofSLRB-r16)) OF 
      SL-RLC-ModeIndication-r16 OPTIONAL,
   sl-QoS-InfoList-r16 [3] SEQUENCE (SIZE (1..maxNrofSL-QFIsPerDest-r16)) OF SL-QoS-Info-r16 OPTIONAL,
   sl-TypeTxSyncList-r16 [4] SEQUENCE (SIZE (1..maxNrofFreqSL-r16)) OF SL-TypeTxSync-r16 OPTIONAL
      ,
   sl-TxInterestedFreqList-r16 [5] SL-TxInterestedFreqList-r16 OPTIONAL,
   sl-CapabilityInformationSidelink-r16 [6] OCTET STRING OPTIONAL
}

SL-TxResourceReqList-r16 ::= SEQUENCE (SIZE (1..maxNrofSL-Dest-r16)) OF SL-TxResourceReq-r16

SL-Failure-r16 ::= SEQUENCE {
   sl-DestinationIdentity-r16 [0] SL-DestinationIdentity-r16,
   sl-Failure-r16 [1] ENUMERATED { rlf(0), configFailure(1), drxReject-v1710(2)
      , spare5(3), spare4(4), spare3(5), spare2(6), spare1(7) }
}

SL-FailureList-r16 ::= SEQUENCE (SIZE (1..maxNrofSL-Dest-r16)) OF SL-Failure-r16

-- TAG-SL-DRX-CONFIGUC-STOP
-- TAG-DRX-CONFIGUCSEMISTATIC-START
SL-DRX-ConfigUC-SemiStatic-r17 ::= SEQUENCE {
   sl-drx-onDurationTimer-r17 [0] EXPLICIT CHOICE {
      subMilliSeconds [0] INTEGER (1..31),
      milliSeconds [1] ENUMERATED { ms1(0), ms2(1), ms3(2), ms4(3), ms5(4), 
         ms6(5), ms8(6), ms10(7), ms20(8), ms30(9), ms40(10), ms50(11), 
         ms60(12), ms80(13), ms100(14), ms200(15), ms300(16), ms400(17), 
         ms500(18), ms600(19), ms800(20), ms1000(21), ms1200(22), ms1600(23), 
         spare8(24), spare7(25), spare6(26), spare5(27), spare4(28), spare3(29)
         , spare2(30), spare1(31) }
   },
   sl-drx-CycleStartOffset-r17 [1] EXPLICIT CHOICE {
      ms10 [0] INTEGER (0..9),
      ms20 [1] INTEGER (0..19),
      ms32 [2] INTEGER (0..31),
      ms40 [3] INTEGER (0..39),
      ms60 [4] INTEGER (0..59),
      ms64 [5] INTEGER (0..63),
      ms70 [6] INTEGER (0..69),
      ms80 [7] INTEGER (0..79),
      ms128 [8] INTEGER (0..127),
      ms160 [9] INTEGER (0..159),
      ms256 [10] INTEGER (0..255),
      ms320 [11] INTEGER (0..319),
      ms512 [12] INTEGER (0..511),
      ms640 [13] INTEGER (0..639),
      ms1024 [14] INTEGER (0..1023),
      ms1280 [15] INTEGER (0..1279),
      ms2048 [16] INTEGER (0..2047),
      ms2560 [17] INTEGER (0..2559),
      ms5120 [18] INTEGER (0..5119),
      ms10240 [19] INTEGER (0..10239)
   },
   sl-drx-SlotOffset-r17 [2] INTEGER (0..31)
}

SL-TxResourceReq-v1700 ::= SEQUENCE {
   sl-DRX-InfoFromRxList-r17 [0] SEQUENCE (SIZE (1..maxNrofSL-RxInfoSet-r17)) OF 
      SL-DRX-ConfigUC-SemiStatic-r17 OPTIONAL,
   sl-DRX-Indication-r17 [1] ENUMERATED { on(0), off(1) } OPTIONAL,
   ...
}

SL-TxResourceReqList-v1700 ::= SEQUENCE (SIZE (1..maxNrofSL-Dest-r16)) OF SL-TxResourceReq-v1700

SL-RxDRX-Report-v1700 ::= SEQUENCE {
   sl-DRX-ConfigFromTx-r17 [0] SL-DRX-ConfigUC-SemiStatic-r17,
   ...
}

SL-RxDRX-ReportList-v1700 ::= SEQUENCE (SIZE (1..maxNrofSL-Dest-r16)) OF SL-RxDRX-Report-v1700

SL-RxInterestedGC-BC-Dest-r17 ::= SEQUENCE {
   sl-RxInterestedQoS-InfoList-r17 [0] SEQUENCE (SIZE (1..maxNrofSL-QFIsPerDest-r16)) OF SL-QoS-Info-r16,
   sl-DestinationIdentity-r16 [1] SL-DestinationIdentity-r16
}

SL-RxInterestedGC-BC-DestList-r17 ::= SEQUENCE (SIZE (1..maxNrofSL-Dest-r16)) OF 
   SL-RxInterestedGC-BC-Dest-r17

SL-TxResourceReqDisc-r17 ::= SEQUENCE {
   sl-DestinationIdentityDisc-r17 [0] SL-DestinationIdentity-r16,
   sl-SourceIdentityRelayUE-r17 [1] SL-SourceIdentity-r17 OPTIONAL,
   sl-CastTypeDisc-r17 [2] ENUMERATED { broadcast(0), groupcast(1), unicast(2)
      , spare1(3) },
   sl-TxInterestedFreqListDisc-r17 [3] SL-TxInterestedFreqList-r16,
   sl-TypeTxSyncListDisc-r17 [4] SEQUENCE (SIZE (1..maxNrofFreqSL-r16)) OF SL-TypeTxSync-r16,
   sl-DiscoveryType-r17 [5] ENUMERATED { relay(0), non-Relay(1) },
   ...
}

SL-TxResourceReqListDisc-r17 ::= SEQUENCE (SIZE (1..maxNrofSL-Dest-r16)) OF 
   SL-TxResourceReqDisc-r17

-- TAG-SL-MEASOBJECTLIST-STOP
-- TAG-SL-PAGINGIDENTITYREMOTEUE-START
SL-PagingIdentityRemoteUE-r17 ::= SEQUENCE {
   ng-5G-S-TMSI-r17 [0] NG-5G-S-TMSI,
   fullI-RNTI-r17 [1] I-RNTI-Value OPTIONAL -- Need R
}

SL-TxResourceReqL2U2N-Relay-r17 ::= SEQUENCE {
   sl-DestinationIdentityL2U2N-r17 [0] SL-DestinationIdentity-r16 OPTIONAL,
   sl-TxInterestedFreqListL2U2N-r17 [1] SL-TxInterestedFreqList-r16,
   sl-TypeTxSyncListL2U2N-r17 [2] SEQUENCE (SIZE (1..maxNrofFreqSL-r16)) OF SL-TypeTxSync-r16,
   sl-LocalID-Request-r17 [3] ENUMERATED { true(0) } OPTIONAL,
   sl-PagingIdentityRemoteUE-r17 [4] SL-PagingIdentityRemoteUE-r17 OPTIONAL,
   sl-CapabilityInformationSidelink-r17 [5] OCTET STRING OPTIONAL,
   ...
}

SL-TxResourceReqCommRelay-r17 ::= CHOICE {
   sl-TxResourceReqL2U2N-Relay-r17 [0] SL-TxResourceReqL2U2N-Relay-r17,
   sl-TxResourceReqL3U2N-Relay-r17 [1] SL-TxResourceReq-r16
}

SL-TxResourceReqCommRelayInfo-r17 ::= SEQUENCE {
   sl-RelayDRXConfig-r17 [0] SL-TxResourceReq-v1700 OPTIONAL,
   sl-TxResourceReqCommRelay-r17 [1] EXPLICIT SL-TxResourceReqCommRelay-r17
}

SL-TxResourceReqListCommRelay-r17 ::= SEQUENCE (SIZE (1..maxNrofSL-Dest-r16)) OF 
   SL-TxResourceReqCommRelayInfo-r17

SidelinkUEInformationNR-v1700-IEs ::= SEQUENCE {
   sl-TxResourceReqList-v1700 [0] SL-TxResourceReqList-v1700 OPTIONAL,
   sl-RxDRX-ReportList-v1700 [1] SL-RxDRX-ReportList-v1700 OPTIONAL,
   sl-RxInterestedGC-BC-DestList-r17 [2] SL-RxInterestedGC-BC-DestList-r17
       OPTIONAL,
   sl-RxInterestedFreqListDisc-r17 [3] SL-InterestedFreqList-r16 OPTIONAL,
   sl-TxResourceReqListDisc-r17 [4] SL-TxResourceReqListDisc-r17 OPTIONAL,
   sl-TxResourceReqListCommRelay-r17 [5] SL-TxResourceReqListCommRelay-r17
       OPTIONAL,
   ue-Type-r17 [6] ENUMERATED { relayUE(0), remoteUE(1) } OPTIONAL,
   sl-SourceIdentityRemoteUE-r17 [7] SL-SourceIdentity-r17 OPTIONAL,
   nonCriticalExtension [8] SEQUENCE {

   } OPTIONAL
}

SidelinkUEInformationNR-r16-IEs ::= SEQUENCE {
   sl-RxInterestedFreqList-r16 [0] SL-InterestedFreqList-r16 OPTIONAL,
   sl-TxResourceReqList-r16 [1] SL-TxResourceReqList-r16 OPTIONAL,
   sl-FailureList-r16 [2] SL-FailureList-r16 OPTIONAL,
   lateNonCriticalExtension [3] OCTET STRING OPTIONAL,
   nonCriticalExtension [4] SidelinkUEInformationNR-v1700-IEs OPTIONAL
}

-- TAG-SIB1-STOP
-- TAG-SIDELINKUEINFORMATIONNR-START
SidelinkUEInformationNR-r16 ::= SEQUENCE {
   criticalExtensions [0] EXPLICIT CHOICE {
      sidelinkUEInformationNR-r16 [0] SidelinkUEInformationNR-r16-IEs,
      criticalExtensionsFuture [1] SEQUENCE {

      }
   }
}

ULInformationTransferIRAT-r16-IEs ::= SEQUENCE {
   ul-DCCH-MessageEUTRA-r16 [0] OCTET STRING OPTIONAL,
   lateNonCriticalExtension [1] OCTET STRING OPTIONAL,
   nonCriticalExtension [2] SEQUENCE {

   } OPTIONAL
}

-- TAG-ULINFORMATIONTRANSFER-STOP
-- TAG-ULINFORMATIONTRANSFERIRAT-START
ULInformationTransferIRAT-r16 ::= SEQUENCE {
   criticalExtensions [0] EXPLICIT CHOICE {
      c1 [0] EXPLICIT CHOICE {
         ulInformationTransferIRAT-r16 [0] ULInformationTransferIRAT-r16-IEs,
         spare3 [1] NULL,
         spare2 [2] NULL,
         spare1 [3] NULL
      },
      criticalExtensionsFuture [1] SEQUENCE {

      }
   }
}

IAB-IP-AddressNumReq-r16 ::= SEQUENCE {
   all-Traffic-NumReq-r16 [0] INTEGER (1..8) OPTIONAL,
   f1-C-Traffic-NumReq-r16 [1] INTEGER (1..8) OPTIONAL,
   f1-U-Traffic-NumReq-r16 [2] INTEGER (1..8) OPTIONAL,
   non-F1-Traffic-NumReq-r16 [3] INTEGER (1..8) OPTIONAL,
   ...
}

IAB-IP-AddressPrefixReq-r16 ::= SEQUENCE {
   all-Traffic-PrefixReq-r16 [0] ENUMERATED { true(0) } OPTIONAL,
   f1-C-Traffic-PrefixReq-r16 [1] ENUMERATED { true(0) } OPTIONAL,
   f1-U-Traffic-PrefixReq-r16 [2] ENUMERATED { true(0) } OPTIONAL,
   non-F1-Traffic-PrefixReq-r16 [3] ENUMERATED { true(0) } OPTIONAL,
   ...
}

IAB-IP-AddressAndTraffic-r16 ::= SEQUENCE {
   all-Traffic-IAB-IP-Address-r16 [0] SEQUENCE (SIZE (1..8)) OF 
      IAB-IP-Address-r16 OPTIONAL,
   f1-C-Traffic-IP-Address-r16 [1] SEQUENCE (SIZE (1..8)) OF IAB-IP-Address-r16
       OPTIONAL,
   f1-U-Traffic-IP-Address-r16 [2] SEQUENCE (SIZE (1..8)) OF IAB-IP-Address-r16
       OPTIONAL,
   non-F1-Traffic-IP-Address-r16 [3] SEQUENCE (SIZE (1..8)) OF IAB-IP-Address-r16
       OPTIONAL
}

IAB-IP-PrefixAndTraffic-r16 ::= SEQUENCE {
   all-Traffic-IAB-IP-Address-r16 [0] EXPLICIT IAB-IP-Address-r16 OPTIONAL,
   f1-C-Traffic-IP-Address-r16 [1] EXPLICIT IAB-IP-Address-r16 OPTIONAL,
   f1-U-Traffic-IP-Address-r16 [2] EXPLICIT IAB-IP-Address-r16 OPTIONAL,
   non-F1-Traffic-IP-Address-r16 [3] EXPLICIT IAB-IP-Address-r16 OPTIONAL
}

IABOtherInformation-r16-IEs ::= SEQUENCE {
   ip-InfoType-r16 [0] EXPLICIT CHOICE {
      iab-IP-Request-r16 [0] SEQUENCE {
         iab-IPv4-AddressNumReq-r16 [0] IAB-IP-AddressNumReq-r16 OPTIONAL,
         iab-IPv6-AddressReq-r16 [1] EXPLICIT CHOICE {
            iab-IPv6-AddressNumReq-r16 [0] IAB-IP-AddressNumReq-r16,
            iab-IPv6-AddressPrefixReq-r16 [1] IAB-IP-AddressPrefixReq-r16,
            ...
         } OPTIONAL
      },
      iab-IP-Report-r16 [1] SEQUENCE {
         iab-IPv4-AddressReport-r16 [0] IAB-IP-AddressAndTraffic-r16 OPTIONAL,
         iab-IPv6-Report-r16 [1] EXPLICIT CHOICE {
            iab-IPv6-AddressReport-r16 [0] IAB-IP-AddressAndTraffic-r16,
            iab-IPv6-PrefixReport-r16 [1] IAB-IP-PrefixAndTraffic-r16,
            ...
         } OPTIONAL
      },
      ...
   },
   lateNonCriticalExtension [1] OCTET STRING OPTIONAL,
   nonCriticalExtension [2] SEQUENCE {

   } OPTIONAL
}

-- TAG-FAILUREINFORMATION-STOP
-- TAG-IABOTHERINFORMATION-START
IABOtherInformation-r16 ::= SEQUENCE {
   rrc-TransactionIdentifier [0] RRC-TransactionIdentifier,
   criticalExtensions [1] EXPLICIT CHOICE {
      iabOtherInformation-r16 [0] IABOtherInformation-r16-IEs,
      criticalExtensionsFuture [1] SEQUENCE {

      }
   }
}

-- TAG-SLRB-UU-CONFIGINDEX-STOP
-- TAG-CARRIERFREQLISTMBS-START
CarrierFreqListMBS-r17 ::= SEQUENCE (SIZE (1..maxFreqMBS-r17)) OF ARFCN-ValueNR

MBS-ServiceInfo-r17 ::= SEQUENCE {
   tmgi-r17 [0] TMGI-r17
}

-- TAG-MBS-NEIGHBOURCELLLIST-STOP
-- TAG-MBS-SERVICELIST-START
MBS-ServiceList-r17 ::= SEQUENCE (SIZE (1..maxNrofMBS-ServiceListPerUE-r17)) OF MBS-ServiceInfo-r17

MBSInterestIndication-r17-IEs ::= SEQUENCE {
   mbs-FreqList-r17 [0] CarrierFreqListMBS-r17 OPTIONAL,
   mbs-Priority-r17 [1] ENUMERATED { true(0) } OPTIONAL,
   mbs-ServiceList-r17 [2] MBS-ServiceList-r17 OPTIONAL,
   lateNonCriticalExtension [3] OCTET STRING OPTIONAL,
   nonCriticalExtension [4] SEQUENCE {

   } OPTIONAL
}

-- TAG-MBSBROADCASTCONFIGURATION-STOP
-- TAG-MBSINTERESTINDICATION-START
MBSInterestIndication-r17 ::= SEQUENCE {
   criticalExtensions [0] EXPLICIT CHOICE {
      mbsInterestIndication-r17 [0] MBSInterestIndication-r17-IEs,
      criticalExtensionsFuture [1] SEQUENCE {

      }
   }
}

NR-TimeStamp-r17 ::= SEQUENCE {
   nr-SFN-r17 [0] INTEGER (0..1023),
   nr-Slot-r17 [1] EXPLICIT CHOICE {
      scs15-r17 [0] INTEGER (0..9),
      scs30-r17 [1] INTEGER (0..19),
      scs60-r17 [2] INTEGER (0..39),
      scs120-r17 [3] INTEGER (0..79)
   },
   ...
}

UE-TxTEG-Association-r17 ::= SEQUENCE {
   ue-TxTEG-ID-r17 [0] INTEGER (0..maxNrOfTxTEG-ID-1-r17),
   nr-TimeStamp-r17 [1] NR-TimeStamp-r17,
   associatedSRS-PosResourceIdList-r17 [2] SEQUENCE (SIZE (1..maxNrofSRS-PosResources-r16)) OF 
      SRS-PosResourceId-r16,
   servCellId-r17 [3] ServCellIndex OPTIONAL
}

UE-TxTEG-AssociationList-r17 ::= SEQUENCE (SIZE (1..maxNrOfTxTEGReport-r17)) OF 
   UE-TxTEG-Association-r17

UEPositioningAssistanceInfo-v1720-IEs ::= SEQUENCE {
   ue-TxTEG-TimingErrorMarginValue-r17 [0] ENUMERATED { tc0(0), tc2(1), tc4(2)
      , tc6(3), tc8(4), tc12(5), tc16(6), tc20(7), tc24(8), tc32(9), tc40(10), 
      tc48(11), tc56(12), tc64(13), tc72(14), tc80(15) } OPTIONAL,
   nonCriticalExtension [1] SEQUENCE {

   } OPTIONAL
}

UEPositioningAssistanceInfo-r17-IEs ::= SEQUENCE {
   ue-TxTEG-AssociationList-r17 [0] UE-TxTEG-AssociationList-r17 OPTIONAL,
   lateNonCriticalExtension [1] OCTET STRING OPTIONAL,
   nonCriticalExtension [2] UEPositioningAssistanceInfo-v1720-IEs OPTIONAL
}

-- TAG-UEINFORMATIONRESPONSE-STOP
-- TAG-UEPOSITIONINGASSISTANCEINFO-START
UEPositioningAssistanceInfo-r17 ::= SEQUENCE {
   criticalExtensions [0] EXPLICIT CHOICE {
      uePositioningAssistanceInfo-r17 [0] UEPositioningAssistanceInfo-r17-IEs,
      criticalExtensionsFuture [1] SEQUENCE {

      }
   }
}

RAN-VisibleMeasurements-r17 ::= SEQUENCE {
   appLayerBufferLevelList-r17 [0] SEQUENCE (SIZE (1..8)) OF 
      AppLayerBufferLevel-r17 OPTIONAL,
   playoutDelayForMediaStartup-r17 [1] INTEGER (0..30000) OPTIONAL,
   pdu-SessionIdList-r17 [2] SEQUENCE (SIZE (1..maxNrofPDU-Sessions-r17)) OF PDU-SessionID OPTIONAL,
   ...
}

MeasReportAppLayer-r17 ::= SEQUENCE {
   measConfigAppLayerId-r17 [0] MeasConfigAppLayerId-r17,
   measReportAppLayerContainer-r17 [1] OCTET STRING OPTIONAL,
   appLayerSessionStatus-r17 [2] ENUMERATED { start(0), stop(1) } OPTIONAL,
   ran-VisibleMeasurements-r17 [3] RAN-VisibleMeasurements-r17 OPTIONAL
}

MeasurementReportAppLayerList-r17 ::= SEQUENCE (SIZE (1..maxNrofAppLayerMeas-r17)) OF 
   MeasReportAppLayer-r17

MeasurementReportAppLayer-r17-IEs ::= SEQUENCE {
   measurementReportAppLayerList-r17 [0] MeasurementReportAppLayerList-r17,
   lateNonCriticalExtension [1] OCTET STRING OPTIONAL,
   nonCriticalExtension [2] SEQUENCE {

   } OPTIONAL
}

-- TAG-MEASUREMENTREPORT-STOP
-- TAG-MEASUREMENTREPORTAPPLAYER-START
MeasurementReportAppLayer-r17 ::= SEQUENCE {
   criticalExtensions [0] EXPLICIT CHOICE {
      measurementReportAppLayer-r17 [0] MeasurementReportAppLayer-r17-IEs,
      criticalExtensionsFuture [1] SEQUENCE {

      }
   }
}

UL-DCCH-MessageType ::= CHOICE {
   c1 [0] EXPLICIT CHOICE {
      measurementReport [0] MeasurementReport,
      rrcReconfigurationComplete [1] RRCReconfigurationComplete,
      rrcSetupComplete [2] RRCSetupComplete,
      rrcReestablishmentComplete [3] RRCReestablishmentComplete,
      rrcResumeComplete [4] RRCResumeComplete,
      securityModeComplete [5] SecurityModeComplete,
      securityModeFailure [6] SecurityModeFailure,
      ulInformationTransfer [7] ULInformationTransfer,
      locationMeasurementIndication [8] LocationMeasurementIndication,
      ueCapabilityInformation [9] UECapabilityInformation,
      counterCheckResponse [10] CounterCheckResponse,
      ueAssistanceInformation [11] UEAssistanceInformation,
      failureInformation [12] FailureInformation,
      ulInformationTransferMRDC [13] ULInformationTransferMRDC,
      scgFailureInformation [14] SCGFailureInformation,
      scgFailureInformationEUTRA [15] SCGFailureInformationEUTRA
   },
   messageClassExtension [1] EXPLICIT CHOICE {
      c2 [0] EXPLICIT CHOICE {
         ulDedicatedMessageSegment-r16 [0] ULDedicatedMessageSegment-r16,
         dedicatedSIBRequest-r16 [1] DedicatedSIBRequest-r16,
         mcgFailureInformation-r16 [2] MCGFailureInformation-r16,
         ueInformationResponse-r16 [3] UEInformationResponse-r16,
         sidelinkUEInformationNR-r16 [4] SidelinkUEInformationNR-r16,
         ulInformationTransferIRAT-r16 [5] ULInformationTransferIRAT-r16,
         iabOtherInformation-r16 [6] IABOtherInformation-r16,
         mbsInterestIndication-r17 [7] MBSInterestIndication-r17,
         uePositioningAssistanceInfo-r17 [8] UEPositioningAssistanceInfo-r17,
         measurementReportAppLayer-r17 [9] MeasurementReportAppLayer-r17,
         spare6 [10] NULL,
         spare5 [11] NULL,
         spare4 [12] NULL,
         spare3 [13] NULL,
         spare2 [14] NULL,
         spare1 [15] NULL
      },
      messageClassExtensionFuture-r16 [1] SEQUENCE {

      }
   }
}

-- TAG-UL-CCCH1-MESSAGE-STOP
-- TAG-UL-DCCH-MESSAGE-START
UL-DCCH-Message ::= SEQUENCE {
   message [0] EXPLICIT UL-DCCH-MessageType
}

-- TAG-SL-BWP-POOLCONFIG-STOP
-- TAG-SL-BWP-POOLCONFIGCOMMON-START
SL-BWP-PoolConfigCommon-r16 ::= SEQUENCE {
   sl-RxPool-r16 [0] SEQUENCE (SIZE (1..maxNrofRXPool-r16)) OF SL-ResourcePool-r16 OPTIONAL, -- Need R
   sl-TxPoolSelectedNormal-r16 [1] SEQUENCE (SIZE (1..maxNrofTXPool-r16)) OF 
      SL-ResourcePoolConfig-r16 OPTIONAL, -- Need R
   sl-TxPoolExceptional-r16 [2] SL-ResourcePoolConfig-r16 OPTIONAL -- Need R
}

-- TAG-SL-BWP-DISCPOOLCONFIG-STOP
-- TAG-SL-BWP-DISCPOOLCONFIGCOMMON-START
SL-BWP-DiscPoolConfigCommon-r17 ::= SEQUENCE {
   sl-DiscRxPool-r17 [0] SEQUENCE (SIZE (1..maxNrofRXPool-r16)) OF SL-ResourcePool-r16 OPTIONAL, -- Need R
   sl-DiscTxPoolSelected-r17 [1] SEQUENCE (SIZE (1..maxNrofTXPool-r16)) OF 
      SL-ResourcePoolConfig-r16 OPTIONAL,
   ...
}

-- TAG-SL-BWP-CONFIG-STOP
-- TAG-SL-BWP-CONFIGCOMMON-START
SL-BWP-ConfigCommon-r16 ::= SEQUENCE {
   sl-BWP-Generic-r16 [0] SL-BWP-Generic-r16 OPTIONAL, -- Need R
   sl-BWP-PoolConfigCommon-r16 [1] SL-BWP-PoolConfigCommon-r16 OPTIONAL,
   ...,
   [[
      sl-BWP-PoolConfigCommonPS-r17 [2] SL-BWP-PoolConfigCommon-r16 OPTIONAL,
      sl-BWP-DiscPoolConfigCommon-r17 [3] SL-BWP-DiscPoolConfigCommon-r17
          OPTIONAL
   ]]
}

-- TAG-SL-FREQCONFIG-STOP
-- TAG-SL-FREQCONFIGCOMMON-START
SL-FreqConfigCommon-r16 ::= SEQUENCE {
   sl-SCS-SpecificCarrierList-r16 [0] SEQUENCE (SIZE (1..maxSCSs)) OF 
      SCS-SpecificCarrier,
   sl-AbsoluteFrequencyPointA-r16 [1] ARFCN-ValueNR,
   sl-AbsoluteFrequencySSB-r16 [2] ARFCN-ValueNR OPTIONAL, -- Need R
   frequencyShift7p5khzSL-r16 [3] ENUMERATED { true(0) } OPTIONAL, -- Cond V2X-SL-Shared
   valueN-r16 [4] INTEGER (-1..1),
   sl-BWP-List-r16 [5] SEQUENCE (SIZE (1..maxNrofSL-BWPs-r16)) OF SL-BWP-ConfigCommon-r16 OPTIONAL
      , -- Need R
   sl-SyncPriority-r16 [6] ENUMERATED { gnss(0), gnbEnb(1) } OPTIONAL, -- Need R
   sl-NbAsSync-r16 [7] BOOLEAN OPTIONAL, -- Need R
   sl-SyncConfigList-r16 [8] SL-SyncConfigList-r16 OPTIONAL,
   ...
}

SL-NR-AnchorCarrierFreqList-r16 ::= SEQUENCE (SIZE (1..maxFreqSL-NR-r16)) OF ARFCN-ValueNR

SL-EUTRA-AnchorCarrierFreqList-r16 ::= SEQUENCE (SIZE (1..maxFreqSL-EUTRA-r16)) OF ARFCN-ValueEUTRA
   

-- TAG-SL-L2REMOTEUE-CONFIG-STOP
-- TAG-SL-MEASCONFIGCOMMON-START
SL-MeasConfigCommon-r16 ::= SEQUENCE {
   sl-MeasObjectListCommon-r16 [0] SL-MeasObjectList-r16 OPTIONAL, -- Need R
   sl-ReportConfigListCommon-r16 [1] SL-ReportConfigList-r16 OPTIONAL, -- Need R
   sl-MeasIdListCommon-r16 [2] SL-MeasIdList-r16 OPTIONAL, -- Need R
   sl-QuantityConfigCommon-r16 [3] SL-QuantityConfig-r16 OPTIONAL,
   ...
}

SL-ConfigCommonNR-r16 ::= SEQUENCE {
   sl-FreqInfoList-r16 [0] SEQUENCE (SIZE (1..maxNrofFreqSL-r16)) OF SL-FreqConfigCommon-r16
       OPTIONAL, -- Need R
   sl-UE-SelectedConfig-r16 [1] SL-UE-SelectedConfig-r16 OPTIONAL, -- Need R
   sl-NR-AnchorCarrierFreqList-r16 [2] SL-NR-AnchorCarrierFreqList-r16 OPTIONAL
      , -- Need R
   sl-EUTRA-AnchorCarrierFreqList-r16 [3] SL-EUTRA-AnchorCarrierFreqList-r16
       OPTIONAL, -- Need R
   sl-RadioBearerConfigList-r16 [4] SEQUENCE (SIZE (1..maxNrofSLRB-r16)) OF 
      SL-RadioBearerConfig-r16 OPTIONAL, -- Need R
   sl-RLC-BearerConfigList-r16 [5] SEQUENCE (SIZE (1..maxSL-LCID-r16)) OF 
      SL-RLC-BearerConfig-r16 OPTIONAL, -- Need R
   sl-MeasConfigCommon-r16 [6] SL-MeasConfigCommon-r16 OPTIONAL, -- Need R
   sl-CSI-Acquisition-r16 [7] ENUMERATED { enabled(0) } OPTIONAL, -- Need R
   sl-OffsetDFN-r16 [8] INTEGER (1..1000) OPTIONAL, -- Need R
   t400-r16 [9] ENUMERATED { ms100(0), ms200(1), ms300(2), ms400(3), ms600(4), 
      ms1000(5), ms1500(6), ms2000(7) } OPTIONAL, -- Need R
   sl-MaxNumConsecutiveDTX-r16 [10] ENUMERATED { n1(0), n2(1), n3(2), n4(3), 
      n6(4), n8(5), n16(6), n32(7) } OPTIONAL, -- Need R
   sl-SSB-PriorityNR-r16 [11] INTEGER (1..8) OPTIONAL -- Need R
}

SL-DiscConfigCommon-r17 ::= SEQUENCE {
   sl-RelayUE-ConfigCommon-r17 [0] SL-RelayUE-Config-r17,
   sl-RemoteUE-ConfigCommon-r17 [1] SL-RemoteUE-Config-r17
}

-- TAG-UE-TIMERSANDCONSTANTS-STOP
-- TAG-UE-TIMERSANDCONSTANTSREMOTEUE-START
UE-TimersAndConstantsRemoteUE-r17 ::= SEQUENCE {
   t300-RemoteUE-r17 [0] ENUMERATED { ms100(0), ms200(1), ms300(2), ms400(3), 
      ms600(4), ms1000(5), ms1500(6), ms2000(7) } OPTIONAL, -- Need S
   t301-RemoteUE-r17 [1] ENUMERATED { ms100(0), ms200(1), ms300(2), ms400(3), 
      ms600(4), ms1000(5), ms1500(6), ms2000(7) } OPTIONAL, -- Need S
   t319-RemoteUE-r17 [2] ENUMERATED { ms100(0), ms200(1), ms300(2), ms400(3), 
      ms600(4), ms1000(5), ms1500(6), ms2000(7) } OPTIONAL,
   ...
}

SIB12-IEs-r16 ::= SEQUENCE {
   sl-ConfigCommonNR-r16 [0] SL-ConfigCommonNR-r16,
   lateNonCriticalExtension [1] OCTET STRING OPTIONAL,
   ...,
   [[
      sl-DRX-ConfigCommonGC-BC-r17 [2] SL-DRX-ConfigGC-BC-r17 OPTIONAL,
      sl-DiscConfigCommon-r17 [3] SL-DiscConfigCommon-r17 OPTIONAL,
      sl-L2U2N-Relay-r17 [4] ENUMERATED { enabled(0) } OPTIONAL,
      sl-NonRelayDiscovery-r17 [5] ENUMERATED { enabled(0) } OPTIONAL,
      sl-L3U2N-RelayDiscovery-r17 [6] ENUMERATED { enabled(0) } OPTIONAL,
      sl-TimersAndConstantsRemoteUE-r17 [7] UE-TimersAndConstantsRemoteUE-r17
          OPTIONAL
   ]]
}

TRS-ResourceSet-r17 ::= SEQUENCE {
   powerControlOffsetSS-r17 [0] ENUMERATED { db-3(0), db0(1), db3(2), db6(3) },
   scramblingID-Info-r17 [1] EXPLICIT CHOICE {
      scramblingIDforCommon-r17 [0] ScramblingId,
      scramblingIDperResourceListWith2-r17 [1] SEQUENCE (SIZE (2)) OF 
         ScramblingId,
      scramblingIDperResourceListWith4-r17 [2] SEQUENCE (SIZE (4)) OF 
         ScramblingId,
      ...
   },
   firstOFDMSymbolInTimeDomain-r17 [2] INTEGER (0..9),
   startingRB-r17 [3] INTEGER (0..maxNrofPhysicalResourceBlocks-1),
   nrofRBs-r17 [4] INTEGER (24..maxNrofPhysicalResourceBlocksPlus1),
   ssb-Index-r17 [5] SSB-Index,
   periodicityAndOffset-r17 [6] EXPLICIT CHOICE {
      slots10 [0] INTEGER (0..9),
      slots20 [1] INTEGER (0..19),
      slots40 [2] INTEGER (0..39),
      slots80 [3] INTEGER (0..79)
   },
   frequencyDomainAllocation-r17 [7] BIT STRING  (SIZE (4)),
   indBitID-r17 [8] INTEGER (0..5),
   nrofResources-r17 [9] ENUMERATED { n2(0), n4(1) }
}

SIB17-IEs-r17 ::= SEQUENCE {
   trs-ResourceSetConfig-r17 [0] SEQUENCE (SIZE (1..maxNrofTRS-ResourceSets-r17)) OF TRS-ResourceSet-r17,
   validityDuration-r17 [1] ENUMERATED { t1(0), t2(1), t4(2), t8(3), t16(4), 
      t32(5), t64(6), t128(7), t256(8), t512(9), infinity(10), spare5(11), 
      spare4(12), spare3(13), spare2(14), spare1(15) } OPTIONAL, -- Need S
   lateNonCriticalExtension [2] OCTET STRING OPTIONAL,
   ...
}

-- TAG-MEASRESULTCELLLISTSFTD-NR-STOP
-- TAG-MEASRESULTCELLLISTSFTD-EUTRA-START
MeasResultCellListSFTD-EUTRA ::= SEQUENCE (SIZE (1..maxCellSFTD)) OF MeasResultSFTD-EUTRA

-- TAG-ACCESSSTRATUMRELEASE-STOP
-- TAG-APPLAYERMEASPARAMETERS-START
AppLayerMeasParameters-r17 ::= SEQUENCE {
   qoe-Streaming-MeasReport-r17 [0] ENUMERATED { supported(0) } OPTIONAL,
   qoe-MTSI-MeasReport-r17 [1] ENUMERATED { supported(0) } OPTIONAL,
   qoe-VR-MeasReport-r17 [2] ENUMERATED { supported(0) } OPTIONAL,
   ran-VisibleQoE-Streaming-MeasReport-r17 [3] ENUMERATED { supported(0) }
       OPTIONAL,
   ran-VisibleQoE-VR-MeasReport-r17 [4] ENUMERATED { supported(0) } OPTIONAL,
   ul-MeasurementReportAppLayer-Seg-r17 [5] ENUMERATED { supported(0) }
       OPTIONAL,
   ...
}

BandParameters ::= CHOICE {
   eutra [0] SEQUENCE {
      bandEUTRA [0] FreqBandIndicatorEUTRA,
      ca-BandwidthClassDL-EUTRA [1] CA-BandwidthClassEUTRA OPTIONAL,
      ca-BandwidthClassUL-EUTRA [2] CA-BandwidthClassEUTRA OPTIONAL
   },
   nr [1] SEQUENCE {
      bandNR [0] FreqBandIndicatorNR,
      ca-BandwidthClassDL-NR [1] CA-BandwidthClassNR OPTIONAL,
      ca-BandwidthClassUL-NR [2] CA-BandwidthClassNR OPTIONAL
   }
}

-- TAG-CA-BANDWIDTHCLASSNR-STOP
-- TAG-CA-PARAMETERSEUTRA-START
CA-ParametersEUTRA ::= SEQUENCE {
   multipleTimingAdvance [0] ENUMERATED { supported(0) } OPTIONAL,
   simultaneousRx-Tx [1] ENUMERATED { supported(0) } OPTIONAL,
   supportedNAICS-2CRS-AP [2] BIT STRING  (SIZE (1..8)) OPTIONAL,
   additionalRx-Tx-PerformanceReq [3] ENUMERATED { supported(0) } OPTIONAL,
   ue-CA-PowerClass-N [4] ENUMERATED { class2(0) } OPTIONAL,
   supportedBandwidthCombinationSetEUTRA-v1530 [5] BIT STRING  (SIZE (1..32))
       OPTIONAL,
   ...
}

-- TAG-CA-PARAMETERSEUTRA-STOP
-- TAG-CA-PARAMETERSNR-START
CA-ParametersNR ::= SEQUENCE {
   dummy [0] ENUMERATED { supported(0) } OPTIONAL,
   parallelTxSRS-PUCCH-PUSCH [1] ENUMERATED { supported(0) } OPTIONAL,
   parallelTxPRACH-SRS-PUCCH-PUSCH [2] ENUMERATED { supported(0) } OPTIONAL,
   simultaneousRxTxInterBandCA [3] ENUMERATED { supported(0) } OPTIONAL,
   simultaneousRxTxSUL [4] ENUMERATED { supported(0) } OPTIONAL,
   diffNumerologyAcrossPUCCH-Group [5] ENUMERATED { supported(0) } OPTIONAL,
   diffNumerologyWithinPUCCH-GroupSmallerSCS [6] ENUMERATED { supported(0) }
       OPTIONAL,
   supportedNumberTAG [7] ENUMERATED { n2(0), n3(1), n4(2) } OPTIONAL,
   ...
}

-- TAG-MODULATIONORDER-STOP
-- TAG-MRDC-PARAMETERS-START
MRDC-Parameters ::= SEQUENCE {
   singleUL-Transmission [0] ENUMERATED { supported(0) } OPTIONAL,
   dynamicPowerSharingENDC [1] ENUMERATED { supported(0) } OPTIONAL,
   tdm-Pattern [2] ENUMERATED { supported(0) } OPTIONAL,
   ul-SharingEUTRA-NR [3] ENUMERATED { tdm(0), fdm(1), both(2) } OPTIONAL,
   ul-SwitchingTimeEUTRA-NR [4] ENUMERATED { type1(0), type2(1) } OPTIONAL,
   simultaneousRxTxInterBandENDC [5] ENUMERATED { supported(0) } OPTIONAL,
   asyncIntraBandENDC [6] ENUMERATED { supported(0) } OPTIONAL,
   ...,
   [[
      dualPA-Architecture [7] ENUMERATED { supported(0) } OPTIONAL,
      intraBandENDC-Support [8] ENUMERATED { non-contiguous(0), both(1) }
          OPTIONAL,
      ul-TimingAlignmentEUTRA-NR [9] ENUMERATED { required(0) } OPTIONAL
   ]]
}

BandCombination ::= SEQUENCE {
   bandList [0] SEQUENCE (SIZE (1..maxSimultaneousBands)) OF BandParameters,
   featureSetCombination [1] FeatureSetCombinationId,
   ca-ParametersEUTRA [2] CA-ParametersEUTRA OPTIONAL,
   ca-ParametersNR [3] CA-ParametersNR OPTIONAL,
   mrdc-Parameters [4] MRDC-Parameters OPTIONAL,
   supportedBandwidthCombinationSet [5] BIT STRING  (SIZE (1..32)) OPTIONAL,
   powerClass-v1530 [6] ENUMERATED { pc2(0) } OPTIONAL
}

-- TAG-APPLAYERMEASPARAMETERS-STOP
-- TAG-BANDCOMBINATIONLIST-START
BandCombinationList ::= SEQUENCE (SIZE (1..maxBandComb)) OF BandCombination

-- TAG-SRS-ALLPOSRESOURCESRRC-INACTIVE-STOP
-- TAG-SRS-SWITCHINGTIMENR-START
SRS-SwitchingTimeNR ::= SEQUENCE {
   switchingTimeDL [0] ENUMERATED { n0us(0), n30us(1), n100us(2), n140us(3), 
      n200us(4), n300us(5), n500us(6), n900us(7) } OPTIONAL,
   switchingTimeUL [1] ENUMERATED { n0us(0), n30us(1), n100us(2), n140us(3), 
      n200us(4), n300us(5), n500us(6), n900us(7) } OPTIONAL
}

-- TAG-SRS-SWITCHINGTIMENR-STOP
-- TAG-SRS-SWITCHINGTIMEEUTRA-START
SRS-SwitchingTimeEUTRA ::= SEQUENCE {
   switchingTimeDL [0] ENUMERATED { n0(0), n0dot5(1), n1(2), n1dot5(3), n2(4), 
      n2dot5(5), n3(6), n3dot5(7), n4(8), n4dot5(9), n5(10), n5dot5(11), n6(12)
      , n6dot5(13), n7(14) } OPTIONAL,
   switchingTimeUL [1] ENUMERATED { n0(0), n0dot5(1), n1(2), n1dot5(3), n2(4), 
      n2dot5(5), n3(6), n3dot5(7), n4(8), n4dot5(9), n5(10), n5dot5(11), n6(12)
      , n6dot5(13), n7(14) } OPTIONAL
}

BandParameters-v1540 ::= SEQUENCE {
   srs-CarrierSwitch [0] EXPLICIT CHOICE {
      nr [0] SEQUENCE {
         srs-SwitchingTimesListNR [0] SEQUENCE (SIZE (1..maxSimultaneousBands)) OF 
            SRS-SwitchingTimeNR
      },
      eutra [1] SEQUENCE {
         srs-SwitchingTimesListEUTRA [0] SEQUENCE (SIZE (1..maxSimultaneousBands)) OF 
            SRS-SwitchingTimeEUTRA
      }
   } OPTIONAL,
   srs-TxSwitch [1] SEQUENCE {
      supportedSRS-TxPortSwitch [0] ENUMERATED { t1r2(0), t1r4(1), t2r4(2), 
         t1r4-t2r4(3), t1r1(4), t2r2(5), t4r4(6), notSupported(7) },
      txSwitchImpactToRx [1] INTEGER (1..32) OPTIONAL,
      txSwitchWithAnotherBand [2] INTEGER (1..32) OPTIONAL
   } OPTIONAL
}

CA-ParametersNR-v1540 ::= SEQUENCE {
   simultaneousSRS-AssocCSI-RS-AllCC [0] INTEGER (5..32) OPTIONAL,
   csi-RS-IM-ReceptionForFeedbackPerBandComb [1] SEQUENCE {
      maxNumberSimultaneousNZP-CSI-RS-ActBWP-AllCC [0] INTEGER (1..64) OPTIONAL,
      totalNumberPortsSimultaneousNZP-CSI-RS-ActBWP-AllCC [1] INTEGER (2..256)
          OPTIONAL
   } OPTIONAL,
   simultaneousCSI-ReportsAllCC [2] INTEGER (5..32) OPTIONAL,
   dualPA-Architecture [3] ENUMERATED { supported(0) } OPTIONAL
}

BandCombination-v1540 ::= SEQUENCE {
   bandList-v1540 [0] SEQUENCE (SIZE (1..maxSimultaneousBands)) OF BandParameters-v1540,
   ca-ParametersNR-v1540 [1] CA-ParametersNR-v1540 OPTIONAL
}

BandCombinationList-v1540 ::= SEQUENCE (SIZE (1..maxBandComb)) OF BandCombination-v1540

CA-ParametersNR-v1550 ::= SEQUENCE {
   dummy [0] ENUMERATED { supported(0) } OPTIONAL
}

BandCombination-v1550 ::= SEQUENCE {
   ca-ParametersNR-v1550 [0] CA-ParametersNR-v1550
}

BandCombinationList-v1550 ::= SEQUENCE (SIZE (1..maxBandComb)) OF BandCombination-v1550

CA-ParametersNR-v1560 ::= SEQUENCE {
   diffNumerologyWithinPUCCH-GroupLargerSCS [0] ENUMERATED { supported(0) }
       OPTIONAL
}

-- TAG-CA-PARAMETERSNR-STOP
-- TAG-CA-PARAMETERS-NRDC-START
CA-ParametersNRDC ::= SEQUENCE {
   ca-ParametersNR-ForDC [0] CA-ParametersNR OPTIONAL,
   ca-ParametersNR-ForDC-v1540 [1] CA-ParametersNR-v1540 OPTIONAL,
   ca-ParametersNR-ForDC-v1550 [2] CA-ParametersNR-v1550 OPTIONAL,
   ca-ParametersNR-ForDC-v1560 [3] CA-ParametersNR-v1560 OPTIONAL,
   featureSetCombinationDC [4] FeatureSetCombinationId OPTIONAL
}

CA-ParametersEUTRA-v1560 ::= SEQUENCE {
   fd-MIMO-TotalWeightedLayers [0] INTEGER (2..128) OPTIONAL
}

BandCombination-v1560 ::= SEQUENCE {
   ne-DC-BC [0] ENUMERATED { supported(0) } OPTIONAL,
   ca-ParametersNRDC [1] CA-ParametersNRDC OPTIONAL,
   ca-ParametersEUTRA-v1560 [2] CA-ParametersEUTRA-v1560 OPTIONAL,
   ca-ParametersNR-v1560 [3] CA-ParametersNR-v1560 OPTIONAL
}

BandCombinationList-v1560 ::= SEQUENCE (SIZE (1..maxBandComb)) OF BandCombination-v1560

CA-ParametersEUTRA-v1570 ::= SEQUENCE {
   dl-1024QAM-TotalWeightedLayers [0] INTEGER (0..10) OPTIONAL
}

BandCombination-v1570 ::= SEQUENCE {
   ca-ParametersEUTRA-v1570 [0] CA-ParametersEUTRA-v1570
}

BandCombinationList-v1570 ::= SEQUENCE (SIZE (1..maxBandComb)) OF BandCombination-v1570

MRDC-Parameters-v1580 ::= SEQUENCE {
   dynamicPowerSharingNEDC [0] ENUMERATED { supported(0) } OPTIONAL
}

BandCombination-v1580 ::= SEQUENCE {
   mrdc-Parameters-v1580 [0] MRDC-Parameters-v1580
}

BandCombinationList-v1580 ::= SEQUENCE (SIZE (1..maxBandComb)) OF BandCombination-v1580

MRDC-Parameters-v1590 ::= SEQUENCE {
   interBandContiguousMRDC [0] ENUMERATED { supported(0) } OPTIONAL
}

BandCombination-v1590 ::= SEQUENCE {
   supportedBandwidthCombinationSetIntraENDC [0] BIT STRING  (SIZE (1..32))
       OPTIONAL,
   mrdc-Parameters-v1590 [1] MRDC-Parameters-v1590
}

BandCombinationList-v1590 ::= SEQUENCE (SIZE (1..maxBandComb)) OF BandCombination-v1590

CA-ParametersNR-v15g0 ::= SEQUENCE {
   simultaneousRxTxInterBandCAPerBandPair [0] SimultaneousRxTxPerBandPair
       OPTIONAL,
   simultaneousRxTxSULPerBandPair [1] SimultaneousRxTxPerBandPair OPTIONAL
}

CA-ParametersNRDC-v15g0 ::= SEQUENCE {
   ca-ParametersNR-ForDC-v15g0 [0] CA-ParametersNR-v15g0 OPTIONAL
}

MRDC-Parameters-v15g0 ::= SEQUENCE {
   simultaneousRxTxInterBandENDCPerBandPair [0] SimultaneousRxTxPerBandPair
       OPTIONAL
}

BandCombination-v15g0 ::= SEQUENCE {
   ca-ParametersNR-v15g0 [0] CA-ParametersNR-v15g0 OPTIONAL,
   ca-ParametersNRDC-v15g0 [1] CA-ParametersNRDC-v15g0 OPTIONAL,
   mrdc-Parameters-v15g0 [2] MRDC-Parameters-v15g0 OPTIONAL
}

BandCombinationList-v15g0 ::= SEQUENCE (SIZE (1..maxBandComb)) OF BandCombination-v15g0

MRDC-Parameters-v15n0 ::= SEQUENCE {
   intraBandENDC-Support-UL [0] ENUMERATED { non-contiguous(0), both(1) }
       OPTIONAL
}

BandCombination-v15n0 ::= SEQUENCE {
   mrdc-Parameters-v15n0 [0] MRDC-Parameters-v15n0
}

BandCombinationList-v15n0 ::= SEQUENCE (SIZE (1..maxBandComb)) OF BandCombination-v15n0

BandParameters-v1610 ::= SEQUENCE {
   srs-TxSwitch-v1610 [0] SEQUENCE {
      supportedSRS-TxPortSwitch-v1610 [0] ENUMERATED { t1r1-t1r2(0), 
         t1r1-t1r2-t1r4(1), t1r1-t1r2-t2r2-t2r4(2), t1r1-t1r2-t2r2-t1r4-t2r4(3)
         , t1r1-t2r2(4), t1r1-t2r2-t4r4(5) }
   } OPTIONAL
}

CodebookParameters-v1610 ::= SEQUENCE {
   supportedCSI-RS-ResourceListAlt-r16 [0] SEQUENCE {
      type1-SinglePanel-r16 [0] SEQUENCE (SIZE (1..maxNrofCSI-RS-Resources)) OF INTEGER (0..maxNrofCSI-RS-ResourcesAlt-1-r16) OPTIONAL,
      type1-MultiPanel-r16 [1] SEQUENCE (SIZE (1..maxNrofCSI-RS-Resources)) OF INTEGER (0..maxNrofCSI-RS-ResourcesAlt-1-r16) OPTIONAL,
      type2-r16 [2] SEQUENCE (SIZE (1..maxNrofCSI-RS-Resources)) OF INTEGER (0..maxNrofCSI-RS-ResourcesAlt-1-r16) OPTIONAL,
      type2-PortSelection-r16 [3] SEQUENCE (SIZE (1..maxNrofCSI-RS-Resources)) OF INTEGER (0..maxNrofCSI-RS-ResourcesAlt-1-r16) OPTIONAL
   } OPTIONAL
}

CodebookParametersAdditionPerBC-r16 ::= SEQUENCE {
     -- R1 16-3a Regular eType 2 R=1
   etype2R1-r16 [0] SEQUENCE (SIZE (1..maxNrofCSI-RS-ResourcesExt-r16)) OF INTEGER (0..maxNrofCSI-RS-ResourcesAlt-1-r16) OPTIONAL,
     -- R1 16-3a-1 Regular eType 2 R=2
   etype2R2-r16 [1] SEQUENCE (SIZE (1..maxNrofCSI-RS-ResourcesExt-r16)) OF INTEGER (0..maxNrofCSI-RS-ResourcesAlt-1-r16) OPTIONAL,
     -- R1 16-3b Regular eType 2 R=1 PortSelection
   etype2R1-PortSelection-r16 [2] SEQUENCE (SIZE (1..maxNrofCSI-RS-ResourcesExt-r16)) OF INTEGER (0..maxNrofCSI-RS-ResourcesAlt-1-r16) OPTIONAL
      ,
     -- R1 16-3b-1 Regular eType 2 R=2 PortSelection
   etype2R2-PortSelection-r16 [3] SEQUENCE (SIZE (1..maxNrofCSI-RS-ResourcesExt-r16)) OF INTEGER (0..maxNrofCSI-RS-ResourcesAlt-1-r16) OPTIONAL
}

CodebookComboParametersAdditionPerBC-r16 ::= SEQUENCE {
     -- R1 16-8 Mixed codebook types
   type1SP-Type2-null-r16 [0] SEQUENCE (SIZE (1..maxNrofCSI-RS-ResourcesExt-r16)) OF INTEGER (0..maxNrofCSI-RS-ResourcesAlt-1-r16) OPTIONAL,
   type1SP-Type2PS-null-r16 [1] SEQUENCE (SIZE (1..maxNrofCSI-RS-ResourcesExt-r16)) OF INTEGER (0..maxNrofCSI-RS-ResourcesAlt-1-r16) OPTIONAL,
   type1SP-eType2R1-null-r16 [2] SEQUENCE (SIZE (1..maxNrofCSI-RS-ResourcesExt-r16)) OF INTEGER (0..maxNrofCSI-RS-ResourcesAlt-1-r16) OPTIONAL,
   type1SP-eType2R2-null-r16 [3] SEQUENCE (SIZE (1..maxNrofCSI-RS-ResourcesExt-r16)) OF INTEGER (0..maxNrofCSI-RS-ResourcesAlt-1-r16) OPTIONAL,
   type1SP-eType2R1PS-null-r16 [4] SEQUENCE (SIZE (1..maxNrofCSI-RS-ResourcesExt-r16)) OF INTEGER (0..maxNrofCSI-RS-ResourcesAlt-1-r16)
       OPTIONAL,
   type1SP-eType2R2PS-null-r16 [5] SEQUENCE (SIZE (1..maxNrofCSI-RS-ResourcesExt-r16)) OF INTEGER (0..maxNrofCSI-RS-ResourcesAlt-1-r16)
       OPTIONAL,
   type1SP-Type2-Type2PS-r16 [6] SEQUENCE (SIZE (1..maxNrofCSI-RS-ResourcesExt-r16)) OF INTEGER (0..maxNrofCSI-RS-ResourcesAlt-1-r16) OPTIONAL,
   type1MP-Type2-null-r16 [7] SEQUENCE (SIZE (1..maxNrofCSI-RS-ResourcesExt-r16)) OF INTEGER (0..maxNrofCSI-RS-ResourcesAlt-1-r16) OPTIONAL,
   type1MP-Type2PS-null-r16 [8] SEQUENCE (SIZE (1..maxNrofCSI-RS-ResourcesExt-r16)) OF INTEGER (0..maxNrofCSI-RS-ResourcesAlt-1-r16) OPTIONAL,
   type1MP-eType2R1-null-r16 [9] SEQUENCE (SIZE (1..maxNrofCSI-RS-ResourcesExt-r16)) OF INTEGER (0..maxNrofCSI-RS-ResourcesAlt-1-r16) OPTIONAL,
   type1MP-eType2R2-null-r16 [10] SEQUENCE (SIZE (1..maxNrofCSI-RS-ResourcesExt-r16)) OF INTEGER (0..maxNrofCSI-RS-ResourcesAlt-1-r16) OPTIONAL
      ,
   type1MP-eType2R1PS-null-r16 [11] SEQUENCE (SIZE (1..maxNrofCSI-RS-ResourcesExt-r16)) OF INTEGER (0..maxNrofCSI-RS-ResourcesAlt-1-r16)
       OPTIONAL,
   type1MP-eType2R2PS-null-r16 [12] SEQUENCE (SIZE (1..maxNrofCSI-RS-ResourcesExt-r16)) OF INTEGER (0..maxNrofCSI-RS-ResourcesAlt-1-r16)
       OPTIONAL,
   type1MP-Type2-Type2PS-r16 [13] SEQUENCE (SIZE (1..maxNrofCSI-RS-ResourcesExt-r16)) OF INTEGER (0..maxNrofCSI-RS-ResourcesAlt-1-r16) OPTIONAL
}

CA-ParametersNR-v1610 ::= SEQUENCE {
      -- R1 9-3: Parallel MsgA and SRS/PUCCH/PUSCH transmissions across CCs in inter-band CA
   parallelTxMsgA-SRS-PUCCH-PUSCH-r16 [0] ENUMERATED { supported(0) } OPTIONAL,
      -- R1 9-4: MsgA operation in a band combination including SUL
   msgA-SUL-r16 [1] ENUMERATED { supported(0) } OPTIONAL,
     -- R1 10-9c: Joint search space group switching across multiple cells
   jointSearchSpaceSwitchAcrossCells-r16 [2] ENUMERATED { supported(0) }
       OPTIONAL,
     -- R1 14-5: Half-duplex UE behaviour in TDD CA for same SCS
   half-DuplexTDD-CA-SameSCS-r16 [3] ENUMERATED { supported(0) } OPTIONAL,
     -- R1 18-4: SCell dormancy within active time
   scellDormancyWithinActiveTime-r16 [4] ENUMERATED { supported(0) } OPTIONAL,
     -- R1 18-4a: SCell dormancy outside active time
   scellDormancyOutsideActiveTime-r16 [5] ENUMERATED { supported(0) } OPTIONAL,
     -- R1 18-6: Cross-carrier A-CSI RS triggering with different SCS
   crossCarrierA-CSI-trigDiffSCS-r16 [6] ENUMERATED { higherA-CSI-SCS(0), 
      lowerA-CSI-SCS(1), both(2) } OPTIONAL,
     -- R1 18-6a: Default QCL assumption for cross-carrier A-CSI-RS triggering
   defaultQCL-CrossCarrierA-CSI-Trig-r16 [7] ENUMERATED { diffOnly(0), both(1)
       } OPTIONAL,
     -- R1 18-7: CA with non-aligned frame boundaries for inter-band CA
   interCA-NonAlignedFrame-r16 [8] ENUMERATED { supported(0) } OPTIONAL,
   simul-SRS-Trans-BC-r16 [9] ENUMERATED { n2(0) } OPTIONAL,
   interFreqDAPS-r16 [10] SEQUENCE {
      interFreqAsyncDAPS-r16 [0] ENUMERATED { supported(0) } OPTIONAL,
      interFreqDiffSCS-DAPS-r16 [1] ENUMERATED { supported(0) } OPTIONAL,
      interFreqMultiUL-TransmissionDAPS-r16 [2] ENUMERATED { supported(0) }
          OPTIONAL,
      interFreqSemiStaticPowerSharingDAPS-Mode1-r16 [3] ENUMERATED { 
         supported(0) } OPTIONAL,
      interFreqSemiStaticPowerSharingDAPS-Mode2-r16 [4] ENUMERATED { 
         supported(0) } OPTIONAL,
      interFreqDynamicPowerSharingDAPS-r16 [5] ENUMERATED { short(0), long(1) }
          OPTIONAL,
      interFreqUL-TransCancellationDAPS-r16 [6] ENUMERATED { supported(0) }
          OPTIONAL
   } OPTIONAL,
   codebookParametersPerBC-r16 [11] CodebookParameters-v1610 OPTIONAL,
     -- R1 16-2a-10 Value of R for BD/CCE
   blindDetectFactor-r16 [12] INTEGER (1..2) OPTIONAL,
     -- R1 11-2a: Capability on the number of CCs for monitoring a maximum number of BDs and non-overlapped CCEs per span when configured
     -- with DL CA with Rel-16 PDCCH monitoring capability on all the serving cells
   pdcch-MonitoringCA-r16 [13] SEQUENCE {
      maxNumberOfMonitoringCC-r16 [0] INTEGER (2..16),
      supportedSpanArrangement-r16 [1] ENUMERATED { alignedOnly(0), 
         alignedAndNonAligned(1) }
   } OPTIONAL,
     -- R1 11-2c: Number of carriers for CCE/BD scaling with DL CA with mix of Rel. 16 and Rel. 15 PDCCH monitoring capabilities on
     -- different carriers
   pdcch-BlindDetectionCA-Mixed-r16 [14] SEQUENCE {
      pdcch-BlindDetectionCA1-r16 [0] INTEGER (1..15),
      pdcch-BlindDetectionCA2-r16 [1] INTEGER (1..15),
      supportedSpanArrangement-r16 [2] ENUMERATED { alignedOnly(0), 
         alignedAndNonAligned(1) }
   } OPTIONAL,
     -- R1 11-2d: Capability on the number of CCs for monitoring a maximum number of BDs and non-overlapped CCEs per span for MCG and for
     -- SCG when configured for NR-DC operation with Rel-16 PDCCH monitoring capability on all the serving cells
   pdcch-BlindDetectionMCG-UE-r16 [15] INTEGER (1..14) OPTIONAL,
   pdcch-BlindDetectionSCG-UE-r16 [16] INTEGER (1..14) OPTIONAL,
     -- R1 11-2e: Number of carriers for CCE/BD scaling for MCG and for SCG when configured for NR-DC operation with mix of Rel. 16 and
     -- Rel. 15 PDCCH monitoring capabilities on different carriers
   pdcch-BlindDetectionMCG-UE-Mixed-r16 [17] SEQUENCE {
      pdcch-BlindDetectionMCG-UE1-r16 [0] INTEGER (0..15),
      pdcch-BlindDetectionMCG-UE2-r16 [1] INTEGER (0..15)
   } OPTIONAL,
   pdcch-BlindDetectionSCG-UE-Mixed-r16 [18] SEQUENCE {
      pdcch-BlindDetectionSCG-UE1-r16 [0] INTEGER (0..15),
      pdcch-BlindDetectionSCG-UE2-r16 [1] INTEGER (0..15)
   } OPTIONAL,
      -- R1 18-5 cross-carrier scheduling with different SCS in DL CA
   crossCarrierSchedulingDL-DiffSCS-r16 [19] ENUMERATED { low-to-high(0), 
      high-to-low(1), both(2) } OPTIONAL,
     -- R1 18-5a Default QCL assumption for cross-carrier scheduling
   crossCarrierSchedulingDefaultQCL-r16 [20] ENUMERATED { diff-only(0), both(1)
       } OPTIONAL,
     -- R1 18-5b cross-carrier scheduling with different SCS in UL CA
   crossCarrierSchedulingUL-DiffSCS-r16 [21] ENUMERATED { low-to-high(0), 
      high-to-low(1), both(2) } OPTIONAL,
     -- R1 13.19a Simultaneous positioning SRS and MIMO SRS transmission for a given BC
   simul-SRS-MIMO-Trans-BC-r16 [22] ENUMERATED { n2(0) } OPTIONAL,
     -- R1 16-3a, 16-3a-1, 16-3b, 16-3b-1: New Individual Codebook
   codebookParametersAdditionPerBC-r16 [23] CodebookParametersAdditionPerBC-r16
       OPTIONAL,
     -- R1 16-8: Mixed codebook
   codebookComboParametersAdditionPerBC-r16 [24] 
      CodebookComboParametersAdditionPerBC-r16 OPTIONAL
}

CA-ParametersNRDC-v1610 ::= SEQUENCE {
     -- R1 18-1: Semi-static power sharing mode1 between MCG and SCG cells of same FR for NR dual connectivity
   intraFR-NR-DC-PwrSharingMode1-r16 [0] ENUMERATED { supported(0) } OPTIONAL,
     -- R1 18-1a: Semi-static power sharing mode 2 between MCG and SCG cells of same FR for NR dual connectivity
   intraFR-NR-DC-PwrSharingMode2-r16 [1] ENUMERATED { supported(0) } OPTIONAL,
     -- R1 18-1b: Dynamic power sharing between MCG and SCG cells of same FR for NR dual connectivity
   intraFR-NR-DC-DynamicPwrSharing-r16 [2] ENUMERATED { short(0), long(1) }
       OPTIONAL,
   asyncNRDC-r16 [3] ENUMERATED { supported(0) } OPTIONAL
}

MRDC-Parameters-v1620 ::= SEQUENCE {
   maxUplinkDutyCycle-interBandENDC-TDD-PC2-r16 [0] SEQUENCE {
      eutra-TDD-Config0-r16 [0] ENUMERATED { n20(0), n40(1), n50(2), n60(3), 
         n70(4), n80(5), n90(6), n100(7) } OPTIONAL,
      eutra-TDD-Config1-r16 [1] ENUMERATED { n20(0), n40(1), n50(2), n60(3), 
         n70(4), n80(5), n90(6), n100(7) } OPTIONAL,
      eutra-TDD-Config2-r16 [2] ENUMERATED { n20(0), n40(1), n50(2), n60(3), 
         n70(4), n80(5), n90(6), n100(7) } OPTIONAL,
      eutra-TDD-Config3-r16 [3] ENUMERATED { n20(0), n40(1), n50(2), n60(3), 
         n70(4), n80(5), n90(6), n100(7) } OPTIONAL,
      eutra-TDD-Config4-r16 [4] ENUMERATED { n20(0), n40(1), n50(2), n60(3), 
         n70(4), n80(5), n90(6), n100(7) } OPTIONAL,
      eutra-TDD-Config5-r16 [5] ENUMERATED { n20(0), n40(1), n50(2), n60(3), 
         n70(4), n80(5), n90(6), n100(7) } OPTIONAL,
      eutra-TDD-Config6-r16 [6] ENUMERATED { n20(0), n40(1), n50(2), n60(3), 
         n70(4), n80(5), n90(6), n100(7) } OPTIONAL
   } OPTIONAL,
     -- R1 18-2 Single UL TX operation for TDD PCell in EN-DC
   tdm-restrictionTDD-endc-r16 [1] ENUMERATED { supported(0) } OPTIONAL,
     -- R1 18-2a Single UL TX operation for FDD PCell in EN-DC
   tdm-restrictionFDD-endc-r16 [2] ENUMERATED { supported(0) } OPTIONAL,
     --  R1 18-2b Support of HARQ-offset for SUO case1 in EN-DC with LTE TDD PCell for type 1 UE
   singleUL-HARQ-offsetTDD-PCell-r16 [3] ENUMERATED { supported(0) } OPTIONAL,
     --  R1 18-3 Dual Tx transmission for EN-DC with FDD PCell(TDM pattern for dual Tx UE)
   tdm-restrictionDualTX-FDD-endc-r16 [4] ENUMERATED { supported(0) } OPTIONAL
}

BandCombination-v1610 ::= SEQUENCE {
   bandList-v1610 [0] SEQUENCE (SIZE (1..maxSimultaneousBands)) OF BandParameters-v1610 OPTIONAL,
   ca-ParametersNR-v1610 [1] CA-ParametersNR-v1610 OPTIONAL,
   ca-ParametersNRDC-v1610 [2] CA-ParametersNRDC-v1610 OPTIONAL,
   powerClass-v1610 [3] ENUMERATED { pc1dot5(0) } OPTIONAL,
   powerClassNRPart-r16 [4] ENUMERATED { pc1(0), pc2(1), pc3(2), pc5(3) }
       OPTIONAL,
   featureSetCombinationDAPS-r16 [5] FeatureSetCombinationId OPTIONAL,
   mrdc-Parameters-v1620 [6] MRDC-Parameters-v1620 OPTIONAL
}

BandCombinationList-v1610 ::= SEQUENCE (SIZE (1..maxBandComb)) OF BandCombination-v1610

SimulSRS-ForAntennaSwitching-r16 ::= SEQUENCE {
   supportSRS-xTyR-xLessThanY-r16 [0] ENUMERATED { supported(0) } OPTIONAL,
   supportSRS-xTyR-xEqualToY-r16 [1] ENUMERATED { supported(0) } OPTIONAL,
   supportSRS-AntennaSwitching-r16 [2] ENUMERATED { supported(0) } OPTIONAL
}

CA-ParametersNR-v1630 ::= SEQUENCE {
     -- R1 22-5b: Simultaneous transmission of SRS for antenna switching and SRS for CB/NCB /BM for inter-band UL CA
     -- R1 22-5d: Simultaneous transmission of SRS for antenna switching for inter-band UL CA
   simulTX-SRS-AntSwitchingInterBandUL-CA-r16 [0] 
      SimulSRS-ForAntennaSwitching-r16 OPTIONAL,
     -- R4 8-5: supported beam management type for inter-band CA
   beamManagementType-r16 [1] ENUMERATED { ibm(0), dummy(1) } OPTIONAL,
     -- R4 7-3a: UL frequency separation class with aggregate BW and Gap BW
   intraBandFreqSeparationUL-AggBW-GapBW-r16 [2] ENUMERATED { classI(0), 
      classII(1), classIII(2) } OPTIONAL,
     -- RAN 89: Case B in case of Inter-band CA with non-aligned frame boundaries
   interCA-NonAlignedFrame-B-r16 [3] ENUMERATED { supported(0) } OPTIONAL
}

CA-ParametersNRDC-v1630 ::= SEQUENCE {
   ca-ParametersNR-ForDC-v1610 [0] CA-ParametersNR-v1610 OPTIONAL,
   ca-ParametersNR-ForDC-v1630 [1] CA-ParametersNR-v1630 OPTIONAL
}

MRDC-Parameters-v1630 ::= SEQUENCE {
     -- R4 2-20 Maximum uplink duty cycle for FDD+TDD EN-DC power class 2
   maxUplinkDutyCycle-interBandENDC-FDD-TDD-PC2-r16 [0] SEQUENCE {
      maxUplinkDutyCycle-FDD-TDD-EN-DC1-r16 [0] ENUMERATED { n30(0), n40(1), 
         n50(2), n60(3), n70(4), n80(5), n90(6), n100(7) } OPTIONAL,
      maxUplinkDutyCycle-FDD-TDD-EN-DC2-r16 [1] ENUMERATED { n30(0), n40(1), 
         n50(2), n60(3), n70(4), n80(5), n90(6), n100(7) } OPTIONAL
   } OPTIONAL,
     -- R4 2-19 FDD-FDD or TDD-TDD inter-band MR-DC with overlapping or partially overlapping DL spectrum
   interBandMRDC-WithOverlapDL-Bands-r16 [1] ENUMERATED { supported(0) }
       OPTIONAL
}

BandCombination-v1630 ::= SEQUENCE {
   ca-ParametersNR-v1630 [0] CA-ParametersNR-v1630 OPTIONAL,
   ca-ParametersNRDC-v1630 [1] CA-ParametersNRDC-v1630 OPTIONAL,
   mrdc-Parameters-v1630 [2] MRDC-Parameters-v1630 OPTIONAL,
   supportedTxBandCombListPerBC-Sidelink-r16 [3] BIT STRING  (SIZE (1..maxBandComb))
       OPTIONAL,
   supportedRxBandCombListPerBC-Sidelink-r16 [4] BIT STRING  (SIZE (1..maxBandComb))
       OPTIONAL,
   scalingFactorTxSidelink-r16 [5] SEQUENCE (SIZE (1..maxBandComb)) OF 
      ScalingFactorSidelink-r16 OPTIONAL,
   scalingFactorRxSidelink-r16 [6] SEQUENCE (SIZE (1..maxBandComb)) OF 
      ScalingFactorSidelink-r16 OPTIONAL
}

BandCombinationList-v1630 ::= SEQUENCE (SIZE (1..maxBandComb)) OF BandCombination-v1630

PUCCH-Grp-CarrierTypes-r16 ::= SEQUENCE {
   fr1-NonSharedTDD-r16 [0] ENUMERATED { supported(0) } OPTIONAL,
   fr1-SharedTDD-r16 [1] ENUMERATED { supported(0) } OPTIONAL,
   fr1-NonSharedFDD-r16 [2] ENUMERATED { supported(0) } OPTIONAL,
   fr2-r16 [3] ENUMERATED { supported(0) } OPTIONAL
}

TwoPUCCH-Grp-ConfigParams-r16 ::= SEQUENCE {
   pucch-GroupMapping-r16 [0] PUCCH-Grp-CarrierTypes-r16,
   pucch-TX-r16 [1] PUCCH-Grp-CarrierTypes-r16
}

TwoPUCCH-Grp-Configurations-r16 ::= SEQUENCE {
   pucch-PrimaryGroupMapping-r16 [0] TwoPUCCH-Grp-ConfigParams-r16,
   pucch-SecondaryGroupMapping-r16 [1] TwoPUCCH-Grp-ConfigParams-r16
}

CA-ParametersNR-v1640 ::= SEQUENCE {
     -- R4 7-5: Support of reporting UL Tx DC locations for uplink intra-band CA.
   uplinkTxDC-TwoCarrierReport-r16 [0] ENUMERATED { supported(0) } OPTIONAL,
     -- RAN 22-6: Support of up to 3 different numerologies in the same NR PUCCH group for NR part of EN-DC, NGEN-DC, NE-DC and NR-CA
     -- where UE is not configured with two NR PUCCH groups
   maxUpTo3Diff-NumerologiesConfigSinglePUCCH-grp-r16 [1] 
      PUCCH-Grp-CarrierTypes-r16 OPTIONAL,
     -- RAN 22-6a: Support of up to 4 different numerologies in the same NR PUCCH group for NR part of EN-DC, NGEN-DC, NE-DC and NR-CA
     -- where UE is not configured with two NR PUCCH groups
   maxUpTo4Diff-NumerologiesConfigSinglePUCCH-grp-r16 [2] 
      PUCCH-Grp-CarrierTypes-r16 OPTIONAL,
     -- RAN 22-7: Support two PUCCH groups for NR-CA with 3 or more bands with at least two carrier types
   twoPUCCH-Grp-ConfigurationsList-r16 [3] SEQUENCE (SIZE (1..maxTwoPUCCH-Grp-ConfigList-r16)) OF 
      TwoPUCCH-Grp-Configurations-r16 OPTIONAL,
     -- R1 22-7a: Different numerology across NR PUCCH groups
   diffNumerologyAcrossPUCCH-Group-CarrierTypes-r16 [4] ENUMERATED { 
      supported(0) } OPTIONAL,
     -- R1 22-7b: Different numerologies across NR carriers within the same NR PUCCH group, with PUCCH on a carrier of smaller SCS
   diffNumerologyWithinPUCCH-GroupSmallerSCS-CarrierTypes-r16 [5] ENUMERATED { 
      supported(0) } OPTIONAL,
     -- R1 22-7c: Different numerologies across NR carriers within the same NR PUCCH group, with PUCCH on a carrier of larger SCS
   diffNumerologyWithinPUCCH-GroupLargerSCS-CarrierTypes-r16 [6] ENUMERATED { 
      supported(0) } OPTIONAL,
     -- R1 11-2f: add the replicated FGs of 11-2a/c with restriction for non-aligned span case
     -- with DL CA with Rel-16 PDCCH monitoring capability on all the serving cells
   pdcch-MonitoringCA-NonAlignedSpan-r16 [7] INTEGER (2..16) OPTIONAL,
     -- R1 11-2g: add the replicated FGs of 11-2a/c with restriction for non-aligned span case
   pdcch-BlindDetectionCA-Mixed-NonAlignedSpan-r16 [8] SEQUENCE {
      pdcch-BlindDetectionCA1-r16 [0] INTEGER (1..15),
      pdcch-BlindDetectionCA2-r16 [1] INTEGER (1..15)
   } OPTIONAL
}

CA-ParametersNRDC-v1640 ::= SEQUENCE {
   ca-ParametersNR-ForDC-v1640 [0] CA-ParametersNR-v1640 OPTIONAL
}

BandCombination-v1640 ::= SEQUENCE {
   ca-ParametersNR-v1640 [0] CA-ParametersNR-v1640 OPTIONAL,
   ca-ParametersNRDC-v1640 [1] CA-ParametersNRDC-v1640 OPTIONAL
}

BandCombinationList-v1640 ::= SEQUENCE (SIZE (1..maxBandComb)) OF BandCombination-v1640

CA-ParametersNRDC-v1650 ::= SEQUENCE {
   supportedCellGrouping-r16 [0] BIT STRING  (SIZE (1..maxCellGroupings-r16)) OPTIONAL
}

BandCombination-v1650 ::= SEQUENCE {
   ca-ParametersNRDC-v1650 [0] CA-ParametersNRDC-v1650 OPTIONAL
}

BandCombinationList-v1650 ::= SEQUENCE (SIZE (1..maxBandComb)) OF BandCombination-v1650

BandCombination-v1680 ::= SEQUENCE {
   intrabandConcurrentOperationPowerClass-r16 [0] SEQUENCE (SIZE (1..maxBandComb)) OF 
      IntraBandPowerClass-r16 OPTIONAL
}

BandCombinationList-v1680 ::= SEQUENCE (SIZE (1..maxBandComb)) OF BandCombination-v1680

CarrierTypePair-r16 ::= SEQUENCE {
   carrierForCSI-Measurement-r16 [0] PUCCH-Grp-CarrierTypes-r16,
   carrierForCSI-Reporting-r16 [1] PUCCH-Grp-CarrierTypes-r16
}

CA-ParametersNR-v1690 ::= SEQUENCE {
   csi-ReportingCrossPUCCH-Grp-r16 [0] SEQUENCE {
      computationTimeForA-CSI-r16 [0] ENUMERATED { sameAsNoCross(0), relaxed(1)
          },
      additionalSymbols-r16 [1] SEQUENCE {
         scs-15kHz-additionalSymbols-r16 [0] ENUMERATED { s14(0), s28(1) }
             OPTIONAL,
         scs-30kHz-additionalSymbols-r16 [1] ENUMERATED { s14(0), s28(1) }
             OPTIONAL,
         scs-60kHz-additionalSymbols-r16 [2] ENUMERATED { s14(0), s28(1), 
            s56(2) } OPTIONAL,
         scs-120kHz-additionalSymbols-r16 [3] ENUMERATED { s14(0), s28(1), 
            s56(2) } OPTIONAL
      } OPTIONAL,
      sp-CSI-ReportingOnPUCCH-r16 [2] ENUMERATED { supported(0) } OPTIONAL,
      sp-CSI-ReportingOnPUSCH-r16 [3] ENUMERATED { supported(0) } OPTIONAL,
      carrierTypePairList-r16 [4] SEQUENCE (SIZE (1..maxCarrierTypePairList-r16)) OF CarrierTypePair-r16
   } OPTIONAL
}

BandCombination-v1690 ::= SEQUENCE {
   ca-ParametersNR-v1690 [0] CA-ParametersNR-v1690 OPTIONAL
}

BandCombinationList-v1690 ::= SEQUENCE (SIZE (1..maxBandComb)) OF BandCombination-v1690

PDCCH-BlindDetectionCA-MixedExt-r16 ::= SEQUENCE {
   pdcch-BlindDetectionCA1-r16 [0] INTEGER (1..15),
   pdcch-BlindDetectionCA2-r16 [1] INTEGER (1..15)
}

PDCCH-BlindDetectionCG-UE-MixedExt-r16 ::= SEQUENCE {
   pdcch-BlindDetectionCG-UE1-r16 [0] INTEGER (0..15),
   pdcch-BlindDetectionCG-UE2-r16 [1] INTEGER (0..15)
}

PDCCH-BlindDetectionMixedList-r16 ::= SEQUENCE {
   pdcch-BlindDetectionCA-MixedExt-r16 [0] EXPLICIT CHOICE {
      pdcch-BlindDetectionCA-Mixed-v16a0 [0] 
         PDCCH-BlindDetectionCA-MixedExt-r16,
      pdcch-BlindDetectionCA-Mixed-NonAlignedSpan-v16a0 [1] 
         PDCCH-BlindDetectionCA-MixedExt-r16
   } OPTIONAL,
   pdcch-BlindDetectionCG-UE-MixedExt-r16 [1] SEQUENCE {
      pdcch-BlindDetectionMCG-UE-Mixed-v16a0 [0] 
         PDCCH-BlindDetectionCG-UE-MixedExt-r16,
      pdcch-BlindDetectionSCG-UE-Mixed-v16a0 [1] 
         PDCCH-BlindDetectionCG-UE-MixedExt-r16
   } OPTIONAL
}

CA-ParametersNR-v16a0 ::= SEQUENCE {
   pdcch-BlindDetectionMixedList-r16 [0] SEQUENCE (SIZE (1..maxNrofPdcch-BlindDetectionMixed-1-r16)) OF 
      PDCCH-BlindDetectionMixedList-r16
}

CA-ParametersNRDC-v16a0 ::= SEQUENCE {
   ca-ParametersNR-ForDC-v16a0 [0] CA-ParametersNR-v16a0 OPTIONAL
}

BandCombination-v16a0 ::= SEQUENCE {
   ca-ParametersNR-v16a0 [0] CA-ParametersNR-v16a0 OPTIONAL,
   ca-ParametersNRDC-v16a0 [1] CA-ParametersNRDC-v16a0 OPTIONAL
}

BandCombinationList-v16a0 ::= SEQUENCE (SIZE (1..maxBandComb)) OF BandCombination-v16a0

CodebookParametersfetype2PerBC-r17 ::= SEQUENCE {
     -- R1 23-9-1	Basic Features of Further Enhanced Port-Selection Type II Codebook (FeType-II)
   fetype2basic-r17 [0] SEQUENCE (SIZE (1..maxNrofCSI-RS-ResourcesExt-r16)) OF INTEGER (0..maxNrofCSI-RS-ResourcesAlt-1-r16),
     -- R1 23-9-2	Support of M=2 and R=1 for FeType-II
   fetype2R1-r17 [1] SEQUENCE (SIZE (1..maxNrofCSI-RS-ResourcesExt-r17)) OF INTEGER (0..maxNrofCSI-RS-ResourcesAlt-1-r16) OPTIONAL,
     -- R1 23-9-4	Support of R = 2 for FeType-II
   fetype2R2-r17 [2] SEQUENCE (SIZE (1..maxNrofCSI-RS-ResourcesExt-r17)) OF INTEGER (0..maxNrofCSI-RS-ResourcesAlt-1-r16) OPTIONAL
}

CodebookComboParameterMixedTypePerBC-r17 ::= SEQUENCE {
     -- R1 23-9-5 Active CSI-RS resources and ports for mixed codebook types in any slot
   type1SP-feType2PS-null-r17 [0] SEQUENCE (SIZE (1..maxNrofCSI-RS-ResourcesExt-r16)) OF INTEGER (0..maxNrofCSI-RS-ResourcesAlt-1-r16) OPTIONAL
      ,
   type1SP-feType2PS-M2R1-null-r17 [1] SEQUENCE (SIZE (1..maxNrofCSI-RS-ResourcesExt-r16)) OF INTEGER (0..maxNrofCSI-RS-ResourcesAlt-1-r16)
       OPTIONAL,
   type1SP-feType2PS-M2R2-null-r17 [2] SEQUENCE (SIZE (1..maxNrofCSI-RS-ResourcesExt-r16)) OF INTEGER (0..maxNrofCSI-RS-ResourcesAlt-1-r16)
       OPTIONAL,
   type1SP-Type2-feType2-PS-M1-r17 [3] SEQUENCE (SIZE (1..maxNrofCSI-RS-ResourcesExt-r16)) OF INTEGER (0..maxNrofCSI-RS-ResourcesAlt-1-r16)
       OPTIONAL,
   type1SP-Type2-feType2-PS-M2R1-r17 [4] SEQUENCE (SIZE (1..maxNrofCSI-RS-ResourcesExt-r16)) OF INTEGER (0..maxNrofCSI-RS-ResourcesAlt-1-r16)
       OPTIONAL,
   type1SP-eType2R1-feType2-PS-M1-r17 [5] SEQUENCE (SIZE (1..maxNrofCSI-RS-ResourcesExt-r16)) OF INTEGER (0..maxNrofCSI-RS-ResourcesAlt-1-r16)
       OPTIONAL,
   type1SP-eType2R1-feType2-PS-M2R1-r17 [6] SEQUENCE (SIZE (1..maxNrofCSI-RS-ResourcesExt-r16)) OF INTEGER (0..maxNrofCSI-RS-ResourcesAlt-1-r16
      ) OPTIONAL,
   type1MP-feType2PS-null-r17 [7] SEQUENCE (SIZE (1..maxNrofCSI-RS-ResourcesExt-r16)) OF INTEGER (0..maxNrofCSI-RS-ResourcesAlt-1-r16) OPTIONAL
      ,
   type1MP-feType2PS-M2R1-null-r17 [8] SEQUENCE (SIZE (1..maxNrofCSI-RS-ResourcesExt-r16)) OF INTEGER (0..maxNrofCSI-RS-ResourcesAlt-1-r16)
       OPTIONAL,
   type1MP-feType2PS-M2R2-null-r17 [9] SEQUENCE (SIZE (1..maxNrofCSI-RS-ResourcesExt-r16)) OF INTEGER (0..maxNrofCSI-RS-ResourcesAlt-1-r16)
       OPTIONAL,
   type1MP-Type2-feType2-PS-M1-r17 [10] SEQUENCE (SIZE (1..maxNrofCSI-RS-ResourcesExt-r16)) OF INTEGER (0..maxNrofCSI-RS-ResourcesAlt-1-r16)
       OPTIONAL,
   type1MP-Type2-feType2-PS-M2R1-r17 [11] SEQUENCE (SIZE (1..maxNrofCSI-RS-ResourcesExt-r16)) OF INTEGER (0..maxNrofCSI-RS-ResourcesAlt-1-r16)
       OPTIONAL,
   type1MP-eType2R1-feType2-PS-M1-r17 [12] SEQUENCE (SIZE (1..maxNrofCSI-RS-ResourcesExt-r16)) OF INTEGER (0..maxNrofCSI-RS-ResourcesAlt-1-r16)
       OPTIONAL,
   type1MP-eType2R1-feType2-PS-M2R1-r17 [13] SEQUENCE (SIZE (1..maxNrofCSI-RS-ResourcesExt-r16)) OF INTEGER (0
      ..maxNrofCSI-RS-ResourcesAlt-1-r16) OPTIONAL
}

CSI-MultiTRP-SupportedCombinations-r17 ::= SEQUENCE {
   maxNumTx-Ports-r17 [0] ENUMERATED { n2(0), n4(1), n8(2), n12(3), n16(4), 
      n24(5), n32(6) },
   maxTotalNumCMR-r17 [1] INTEGER (2..64),
   maxTotalNumTx-PortsNZP-CSI-RS-r17 [2] INTEGER (2..256)
}

CodebookComboParameterMultiTRP-PerBC-r17 ::= SEQUENCE {
     -- R1 23-7-1b	Active CSI-RS resources and ports in the presence of multi-TRP CSI
     --  {Codebook 2, Codebook 3} =(NULL, NULL}
   nCJT-null-null [0] SEQUENCE (SIZE (1..maxNrofCSI-RS-ResourcesExt-r16)) OF INTEGER (0..maxNrofCSI-RS-ResourcesAlt-1-r16) OPTIONAL,
   nCJT1SP-null-null [1] SEQUENCE (SIZE (1..maxNrofCSI-RS-ResourcesExt-r16)) OF INTEGER (0..maxNrofCSI-RS-ResourcesAlt-1-r16) OPTIONAL,
     --    {Codebook 2, Codebook 3} = {( {"Rel 16 combinations in FG 16-8"}
   nCJT-Type2-null-r16 [2] SEQUENCE (SIZE (1..maxNrofCSI-RS-ResourcesExt-r16)) OF INTEGER (0..maxNrofCSI-RS-ResourcesAlt-1-r16) OPTIONAL,
   nCJT-Type2PS-null-r16 [3] SEQUENCE (SIZE (1..maxNrofCSI-RS-ResourcesExt-r16)) OF INTEGER (0..maxNrofCSI-RS-ResourcesAlt-1-r16) OPTIONAL,
   nCJT-eType2R1-null-r16 [4] SEQUENCE (SIZE (1..maxNrofCSI-RS-ResourcesExt-r16)) OF INTEGER (0..maxNrofCSI-RS-ResourcesAlt-1-r16) OPTIONAL,
   nCJT-eType2R2-null-r16 [5] SEQUENCE (SIZE (1..maxNrofCSI-RS-ResourcesExt-r16)) OF INTEGER (0..maxNrofCSI-RS-ResourcesAlt-1-r16) OPTIONAL,
   nCJT-eType2R1PS-null-r16 [6] SEQUENCE (SIZE (1..maxNrofCSI-RS-ResourcesExt-r16)) OF INTEGER (0..maxNrofCSI-RS-ResourcesAlt-1-r16) OPTIONAL,
   nCJT-eType2R2PS-null-r16 [7] SEQUENCE (SIZE (1..maxNrofCSI-RS-ResourcesExt-r16)) OF INTEGER (0..maxNrofCSI-RS-ResourcesAlt-1-r16) OPTIONAL,
   nCJT-Type2-Type2PS-r16 [8] SEQUENCE (SIZE (1..maxNrofCSI-RS-ResourcesExt-r16)) OF INTEGER (0..maxNrofCSI-RS-ResourcesAlt-1-r16) OPTIONAL,
   nCJT1SP-Type2-null-r16 [9] SEQUENCE (SIZE (1..maxNrofCSI-RS-ResourcesExt-r16)) OF INTEGER (0..maxNrofCSI-RS-ResourcesAlt-1-r16) OPTIONAL,
   nCJT1SP-Type2PS-null-r16 [10] SEQUENCE (SIZE (1..maxNrofCSI-RS-ResourcesExt-r16)) OF INTEGER (0..maxNrofCSI-RS-ResourcesAlt-1-r16) OPTIONAL,
   nCJT1SP-eType2R1-null-r16 [11] SEQUENCE (SIZE (1..maxNrofCSI-RS-ResourcesExt-r16)) OF INTEGER (0..maxNrofCSI-RS-ResourcesAlt-1-r16) OPTIONAL
      ,
   nCJT1SP-eType2R2-null-r16 [12] SEQUENCE (SIZE (1..maxNrofCSI-RS-ResourcesExt-r16)) OF INTEGER (0..maxNrofCSI-RS-ResourcesAlt-1-r16) OPTIONAL
      ,
   nCJT1SP-eType2R1PS-null-r16 [13] SEQUENCE (SIZE (1..maxNrofCSI-RS-ResourcesExt-r16)) OF INTEGER (0..maxNrofCSI-RS-ResourcesAlt-1-r16)
       OPTIONAL,
   nCJT1SP-eType2R2PS-null-r16 [14] SEQUENCE (SIZE (1..maxNrofCSI-RS-ResourcesExt-r16)) OF INTEGER (0..maxNrofCSI-RS-ResourcesAlt-1-r16)
       OPTIONAL,
   nCJT1SP-Type2-Type2PS-r16 [15] SEQUENCE (SIZE (1..maxNrofCSI-RS-ResourcesExt-r16)) OF INTEGER (0..maxNrofCSI-RS-ResourcesAlt-1-r16) OPTIONAL
      ,
     -- {Codebook 2, Codebook 3} = {"New Rel17 combinations in FG 23-9-5"}
   nCJT-feType2PS-null-r17 [16] SEQUENCE (SIZE (1..maxNrofCSI-RS-ResourcesExt-r16)) OF INTEGER (0..maxNrofCSI-RS-ResourcesAlt-1-r16) OPTIONAL,
   nCJT-feType2PS-M2R1-null-r17 [17] SEQUENCE (SIZE (1..maxNrofCSI-RS-ResourcesExt-r16)) OF INTEGER (0..maxNrofCSI-RS-ResourcesAlt-1-r16)
       OPTIONAL,
   nCJT-feType2PS-M2R2-null-r17 [18] SEQUENCE (SIZE (1..maxNrofCSI-RS-ResourcesExt-r16)) OF INTEGER (0..maxNrofCSI-RS-ResourcesAlt-1-r16)
       OPTIONAL,
   nCJT-Type2-feType2-PS-M1-r17 [19] SEQUENCE (SIZE (1..maxNrofCSI-RS-ResourcesExt-r16)) OF INTEGER (0..maxNrofCSI-RS-ResourcesAlt-1-r16)
       OPTIONAL,
   nCJT-Type2-feType2-PS-M2R1-r17 [20] SEQUENCE (SIZE (1..maxNrofCSI-RS-ResourcesExt-r16)) OF INTEGER (0..maxNrofCSI-RS-ResourcesAlt-1-r16)
       OPTIONAL,
   nCJT-eType2R1-feType2-PS-M1-r17 [21] SEQUENCE (SIZE (1..maxNrofCSI-RS-ResourcesExt-r16)) OF INTEGER (0..maxNrofCSI-RS-ResourcesAlt-1-r16)
       OPTIONAL,
   nCJT-eType2R1-feType2-PS-M2R1-r17 [22] SEQUENCE (SIZE (1..maxNrofCSI-RS-ResourcesExt-r16)) OF INTEGER (0..maxNrofCSI-RS-ResourcesAlt-1-r16)
       OPTIONAL,
   nCJT1SP-feType2PS-null-r17 [23] SEQUENCE (SIZE (1..maxNrofCSI-RS-ResourcesExt-r16)) OF INTEGER (0..maxNrofCSI-RS-ResourcesAlt-1-r16)
       OPTIONAL,
   nCJT1SP-feType2PS-M2R1-null-r17 [24] SEQUENCE (SIZE (1..maxNrofCSI-RS-ResourcesExt-r16)) OF INTEGER (0..maxNrofCSI-RS-ResourcesAlt-1-r16)
       OPTIONAL,
   nCJT1SP-feType2PS-M2R2-null-r1 [25] SEQUENCE (SIZE (1..maxNrofCSI-RS-ResourcesExt-r16)) OF INTEGER (0..maxNrofCSI-RS-ResourcesAlt-1-r16)
       OPTIONAL,
   nCJT1SP-Type2-feType2-PS-M1-r17 [26] SEQUENCE (SIZE (1..maxNrofCSI-RS-ResourcesExt-r16)) OF INTEGER (0..maxNrofCSI-RS-ResourcesAlt-1-r16)
       OPTIONAL,
   nCJT1SP-Type2-feType2-PS-M2R1-r17 [27] SEQUENCE (SIZE (1..maxNrofCSI-RS-ResourcesExt-r16)) OF INTEGER (0..maxNrofCSI-RS-ResourcesAlt-1-r16)
       OPTIONAL,
   nCJT1SP-eType2R1-feType2-PS-M1-r17 [28] SEQUENCE (SIZE (1..maxNrofCSI-RS-ResourcesExt-r16)) OF INTEGER (0..maxNrofCSI-RS-ResourcesAlt-1-r16)
       OPTIONAL,
   nCJT1SP-eType2R1-feType2-PS-M2R1-r17 [29] SEQUENCE (SIZE (1..maxNrofCSI-RS-ResourcesExt-r16)) OF INTEGER (0
      ..maxNrofCSI-RS-ResourcesAlt-1-r16) OPTIONAL
}

CrossCarrierSchedulingSCell-SpCell-r17 ::= SEQUENCE {
   supportedSCS-Combinations-r17 [0] SEQUENCE {
      scs15kHz-15kHz-r17 [0] ENUMERATED { supported(0) } OPTIONAL,
      scs15kHz-30kHz-r17 [1] ENUMERATED { supported(0) } OPTIONAL,
      scs15kHz-60kHz-r17 [2] ENUMERATED { supported(0) } OPTIONAL,
      scs30kHz-30kHz-r17 [3] BIT STRING  (SIZE (1..496)) OPTIONAL,
      scs30kHz-60kHz-r17 [4] BIT STRING  (SIZE (1..496)) OPTIONAL,
      scs60kHz-60kHz-r17 [5] BIT STRING  (SIZE (1..496)) OPTIONAL
   },
   pdcch-MonitoringOccasion-r17 [1] ENUMERATED { val1(0), val2(1) }
}

CA-ParametersNR-v1700 ::= SEQUENCE {
     -- R1 23-9-1: Basic Features of Further Enhanced Port-Selection Type II Codebook (FeType-II) per band combination information
   codebookParametersfetype2PerBC-r17 [0] CodebookParametersfetype2PerBC-r17
       OPTIONAL,
     -- R4 18-4: Support of enhanced Demodulation requirements for CA in HST SFN FR1
   demodulationEnhancementCA-r17 [1] ENUMERATED { supported(0) } OPTIONAL,
     -- R4 20-1: Maximum uplink duty cycle for NR inter-band CA power class 2
   maxUplinkDutyCycle-interBandCA-PC2-r17 [2] ENUMERATED { n50(0), n60(1), 
      n70(2), n80(3), n90(4), n100(5) } OPTIONAL,
     -- R4 20-2: Maximum uplink duty cycle for NR SUL combination power class 2
   maxUplinkDutyCycle-SULcombination-PC2-r17 [3] ENUMERATED { n50(0), n60(1), 
      n70(2), n80(3), n90(4), n100(5) } OPTIONAL,
   beamManagementType-CBM-r17 [4] ENUMERATED { supported(0) } OPTIONAL,
     -- R1 25-18: Parallel PUCCH and PUSCH transmission across CCs in inter-band CA
   parallelTxPUCCH-PUSCH-r17 [5] ENUMERATED { supported(0) } OPTIONAL,
     -- R1 23-9-5	Active CSI-RS resources and ports for mixed codebook types in any slot per band combination
   codebookComboParameterMixedTypePerBC-r17 [6] 
      CodebookComboParameterMixedTypePerBC-r17 OPTIONAL,
    -- R1 23-7-1	Basic Features of CSI Enhancement for Multi-TRP
   mTRP-CSI-EnhancementPerBC-r17 [7] SEQUENCE {
      maxNumNZP-CSI-RS-r17 [0] INTEGER (2..8),
      cSI-Report-mode-r17 [1] ENUMERATED { mode1(0), mode2(1), both(2) },
      supportedComboAcrossCCs-r17 [2] SEQUENCE (SIZE (1..16)) OF 
         CSI-MultiTRP-SupportedCombinations-r17,
      codebookMode-NCJT-r17 [3] ENUMERATED { mode1(0), mode1And2(1) }
   } OPTIONAL,
      -- R1 23-7-1b	Active CSI-RS resources and ports in the presence of multi-TRP CSI
   codebookComboParameterMultiTRP-PerBC-r17 [8] 
      CodebookComboParameterMultiTRP-PerBC-r17 OPTIONAL,
     -- R1 24-8b: 32 DL HARQ processes for FR 2-2 - maximum number of component carriers
   maxCC-32-DL-HARQ-ProcessFR2-2-r17 [9] ENUMERATED { n1(0), n2(1), n3(2), 
      n4(3), n6(4), n8(5), n16(6), n32(7) } OPTIONAL,
     -- R1 24-9b: 32 UL HARQ processes for FR 2-2 - maximum number of component carriers
   maxCC-32-UL-HARQ-ProcessFR2-2-r17 [10] ENUMERATED { n1(0), n2(1), n3(2), 
      n4(3), n5(4), n8(5), n16(6), n32(7) } OPTIONAL,
     -- R1 34-2: Cross-carrier scheduling from SCell to PCell/PSCell (Type B)
   crossCarrierSchedulingSCell-SpCellTypeB-r17 [11] 
      CrossCarrierSchedulingSCell-SpCell-r17 OPTIONAL,
 -- R1 34-1: Cross-carrier scheduling from SCell to PCell/PSCell with search space restrictions (Type A)
   crossCarrierSchedulingSCell-SpCellTypeA-r17 [12] 
      CrossCarrierSchedulingSCell-SpCell-r17 OPTIONAL,
     -- R1 34-1a: DCI formats on PCell/PSCell USS set(s) support
   dci-FormatsPCellPSCellUSS-Sets-r17 [13] ENUMERATED { supported(0) } OPTIONAL
      ,
     -- R1 34-3: Disabling scaling factor alpha when sSCell is deactivated
   disablingScalingFactorDeactSCell-r17 [14] ENUMERATED { supported(0) }
       OPTIONAL,
     -- R1 34-4: Disabling scaling factor alpha when sSCell is deactivated
   disablingScalingFactorDormantSCell-r17 [15] ENUMERATED { supported(0) }
       OPTIONAL,
     -- R1 34-5: Non-aligned frame boundaries between PCell/PSCell and sSCell
   non-AlignedFrameBoundaries-r17 [16] SEQUENCE {
      scs15kHz-15kHz-r17 [0] BIT STRING  (SIZE (1..496)) OPTIONAL,
      scs15kHz-30kHz-r17 [1] BIT STRING  (SIZE (1..496)) OPTIONAL,
      scs15kHz-60kHz-r17 [2] BIT STRING  (SIZE (1..496)) OPTIONAL,
      scs30kHz-30kHz-r17 [3] BIT STRING  (SIZE (1..496)) OPTIONAL,
      scs30kHz-60kHz-r17 [4] BIT STRING  (SIZE (1..496)) OPTIONAL,
      scs60kHz-60kHz-r17 [5] BIT STRING  (SIZE (1..496)) OPTIONAL
   } OPTIONAL
}

CA-ParametersNRDC-v1700 ::= SEQUENCE {
     -- R1 31-9: Indicates the support of simultaneous transmission and reception of an IAB-node from multiple parent nodes
   simultaneousRxTx-IAB-MultipleParents-r17 [0] ENUMERATED { supported(0) }
       OPTIONAL,
   condPSCellAdditionNRDC-r17 [1] ENUMERATED { supported(0) } OPTIONAL,
   scg-ActivationDeactivationNRDC-r17 [2] ENUMERATED { supported(0) } OPTIONAL,
   scg-ActivationDeactivationResumeNRDC-r17 [3] ENUMERATED { supported(0) }
       OPTIONAL,
   beamManagementType-CBM-r17 [4] ENUMERATED { supported(0) } OPTIONAL
}

MRDC-Parameters-v1700 ::= SEQUENCE {
   condPSCellAdditionENDC-r17 [0] ENUMERATED { supported(0) } OPTIONAL,
   scg-ActivationDeactivationENDC-r17 [1] ENUMERATED { supported(0) } OPTIONAL,
   scg-ActivationDeactivationResumeENDC-r17 [2] ENUMERATED { supported(0) }
       OPTIONAL
}

BandParameters-v1710 ::= SEQUENCE {
     -- R1 23-8-3	SRS Antenna switching for >4Rx
   srs-AntennaSwitchingBeyond4RX-r17 [0] SEQUENCE {
          -- 1. Support of SRS antenna switching xTyR with y>4
      supportedSRS-TxPortSwitchBeyond4Rx-r17 [0] BIT STRING  (SIZE (11)),
          -- 2. Report the entry number of the first-listed band with UL in the band combination that affects this DL
      entryNumberAffectBeyond4Rx-r17 [1] INTEGER (1..32) OPTIONAL,
          -- 3. Report the entry number of the first-listed band with UL in the band combination that switches together with this UL
      entryNumberSwitchBeyond4Rx-r17 [2] INTEGER (1..32) OPTIONAL
   } OPTIONAL
}

BandCombination-v1700 ::= SEQUENCE {
   ca-ParametersNR-v1700 [0] CA-ParametersNR-v1700 OPTIONAL,
   ca-ParametersNRDC-v1700 [1] CA-ParametersNRDC-v1700 OPTIONAL,
   mrdc-Parameters-v1700 [2] MRDC-Parameters-v1700 OPTIONAL,
   bandList-v1710 [3] SEQUENCE (SIZE (1..maxSimultaneousBands)) OF BandParameters-v1710 OPTIONAL,
   supportedBandCombListPerBC-SL-RelayDiscovery-r17 [4] BIT STRING  (SIZE (1..maxBandComb))
       OPTIONAL,
   supportedBandCombListPerBC-SL-NonRelayDiscovery-r17 [5] BIT STRING  (SIZE (1
      ..maxBandComb)) OPTIONAL
}

BandCombinationList-v1700 ::= SEQUENCE (SIZE (1..maxBandComb)) OF BandCombination-v1700

PUCCH-Group-Config-r17 ::= SEQUENCE {
   fr1-FR1-NonSharedTDD-r17 [0] ENUMERATED { supported(0) } OPTIONAL,
   fr2-FR2-NonSharedTDD-r17 [1] ENUMERATED { supported(0) } OPTIONAL,
   fr1-FR2-NonSharedTDD-r17 [2] ENUMERATED { supported(0) } OPTIONAL
}

TwoPUCCH-Grp-Configurations-r17 ::= SEQUENCE {
   primaryPUCCH-GroupConfig-r17 [0] PUCCH-Group-Config-r17,
   secondaryPUCCH-GroupConfig-r17 [1] PUCCH-Group-Config-r17
}

PDCCH-BlindDetectionMCG-SCG-r17 ::= SEQUENCE {
   pdcch-BlindDetectionMCG-UE-r17 [0] INTEGER (1..15),
   pdcch-BlindDetectionSCG-UE-r17 [1] INTEGER (1..15)
}

PDCCH-BlindDetectionCA-Mixed-r17 ::= SEQUENCE {
   pdcch-BlindDetectionCA1-r17 [0] INTEGER (1..15) OPTIONAL,
   pdcch-BlindDetectionCA2-r17 [1] INTEGER (1..15) OPTIONAL
}

PDCCH-BlindDetectionCG-UE-Mixed-r17 ::= SEQUENCE {
   pdcch-BlindDetectionCG-UE1-r17 [0] INTEGER (0..15),
   pdcch-BlindDetectionCG-UE2-r17 [1] INTEGER (0..15)
}

PDCCH-BlindDetectionMixed-r17 ::= SEQUENCE {
   pdcch-BlindDetectionCA-Mixed-r17 [0] PDCCH-BlindDetectionCA-Mixed-r17
       OPTIONAL,
   pdcch-BlindDetectionCG-UE-Mixed-r17 [1] SEQUENCE {
      pdcch-BlindDetectionMCG-UE-Mixed-v17 [0] 
         PDCCH-BlindDetectionCG-UE-Mixed-r17,
      pdcch-BlindDetectionSCG-UE-Mixed-v17 [1] 
         PDCCH-BlindDetectionCG-UE-Mixed-r17
   } OPTIONAL
}

PDCCH-BlindDetectionCA-Mixed1-r17 ::= SEQUENCE {
   pdcch-BlindDetectionCA1-r17 [0] INTEGER (1..15) OPTIONAL,
   pdcch-BlindDetectionCA2-r17 [1] INTEGER (1..15) OPTIONAL,
   pdcch-BlindDetectionCA3-r17 [2] INTEGER (1..15) OPTIONAL
}

PDCCH-BlindDetectionCG-UE-Mixed1-r17 ::= SEQUENCE {
   pdcch-BlindDetectionCG-UE1-r17 [0] INTEGER (0..15),
   pdcch-BlindDetectionCG-UE2-r17 [1] INTEGER (0..15),
   pdcch-BlindDetectionCG-UE3-r17 [2] INTEGER (0..15)
}

PDCCH-BlindDetectionMixed1-r17 ::= SEQUENCE {
   pdcch-BlindDetectionCA-Mixed1-r17 [0] PDCCH-BlindDetectionCA-Mixed1-r17
       OPTIONAL,
   pdcch-BlindDetectionCG-UE-Mixed1-r17 [1] SEQUENCE {
      pdcch-BlindDetectionMCG-UE-Mixed1-v17 [0] 
         PDCCH-BlindDetectionCG-UE-Mixed1-r17,
      pdcch-BlindDetectionSCG-UE-Mixed1-v17 [1] 
         PDCCH-BlindDetectionCG-UE-Mixed1-r17
   } OPTIONAL
}

CA-ParametersNR-v1720 ::= SEQUENCE {
     -- R1 39-1: Parallel SRS and PUCCH/PUSCH transmission across CCs in intra-band non-contiguous CA
   parallelTxSRS-PUCCH-PUSCH-intraBand-r17 [0] ENUMERATED { supported(0) }
       OPTIONAL,
     -- R1 39-2: Parallel PRACH and SRS/PUCCH/PUSCH transmissions across CCs in intra-band non-contiguous CA
   parallelTxPRACH-SRS-PUCCH-PUSCH-intraBand-r17 [1] ENUMERATED { supported(0)
       } OPTIONAL,
     -- R1 25-9: Semi-static PUCCH cell switching for a single PUCCH group only
   semiStaticPUCCH-CellSwitchSingleGroup-r17 [2] SEQUENCE {
      pucch-Group-r17 [0] ENUMERATED { primaryGroupOnly(0), 
         secondaryGroupOnly(1), eitherPrimaryOrSecondaryGroup(2) },
      pucch-Group-Config-r17 [1] PUCCH-Group-Config-r17
   } OPTIONAL,
     -- R1 25-9a: Semi-static PUCCH cell switching for two PUCCH groups
   semiStaticPUCCH-CellSwitchTwoGroups-r17 [3] SEQUENCE (SIZE (1..maxTwoPUCCH-Grp-ConfigList-r17)) OF 
      TwoPUCCH-Grp-Configurations-r17 OPTIONAL,
     -- R1 25-10: PUCCH cell switching based on dynamic indication for same length of overlapping PUCCH slots/sub-slots for a single
     -- PUCCH group only
   dynamicPUCCH-CellSwitchSameLengthSingleGroup-r17 [4] SEQUENCE {
      pucch-Group-r17 [0] ENUMERATED { primaryGroupOnly(0), 
         secondaryGroupOnly(1), eitherPrimaryOrSecondaryGroup(2) },
      pucch-Group-Config-r17 [1] PUCCH-Group-Config-r17
   } OPTIONAL,
     -- R1 25-10a: PUCCH cell switching based on dynamic indication for different length of overlapping PUCCH slots/sub-slots
     -- for a single PUCCH group only
   dynamicPUCCH-CellSwitchDiffLengthSingleGroup-r17 [5] SEQUENCE {
      pucch-Group-r17 [0] ENUMERATED { primaryGroupOnly(0), 
         secondaryGroupOnly(1), eitherPrimaryOrSecondaryGroup(2) },
      pucch-Group-Config-r17 [1] PUCCH-Group-Config-r17
   } OPTIONAL,
     -- R1 25-10b: PUCCH cell switching based on dynamic indication for same length of overlapping PUCCH slots/sub-slots for two PUCCH
     -- groups
   dynamicPUCCH-CellSwitchSameLengthTwoGroups-r17 [6] SEQUENCE (SIZE (1..maxTwoPUCCH-Grp-ConfigList-r17)) OF 
      TwoPUCCH-Grp-Configurations-r17 OPTIONAL,
     -- R1 25-10c: PUCCH cell switching based on dynamic indication for different length of overlapping PUCCH slots/sub-slots for two
     -- PUCCH groups
   dynamicPUCCH-CellSwitchDiffLengthTwoGroups-r17 [7] SEQUENCE (SIZE (1..maxTwoPUCCH-Grp-ConfigList-r17)) OF 
      TwoPUCCH-Grp-Configurations-r17 OPTIONAL,
     -- R1 33-2a: ACK/NACK based HARQ-ACK feedback and RRC-based enabling/disabling ACK/NACK-based
     -- feedback for dynamic scheduling for multicast
   ack-NACK-FeedbackForMulticast-r17 [8] ENUMERATED { supported(0) } OPTIONAL,
     -- R1 33-2d: PTP retransmission for multicast dynamic scheduling
   ptp-Retx-Multicast-r17 [9] ENUMERATED { supported(0) } OPTIONAL,
     -- R1 33-4: NACK-only based HARQ-ACK feedback for RRC-based enabling/disabling multicast with ACK/NACK transforming
   nack-OnlyFeedbackForMulticast-r17 [10] ENUMERATED { supported(0) } OPTIONAL,
     -- R1 33-4a: NACK-only based HARQ-ACK feedback for multicast corresponding to a specific sequence or a PUCCH transmission
   nack-OnlyFeedbackSpecificResourceForMulticast-r17 [11] ENUMERATED { 
      supported(0) } OPTIONAL,
     -- R1 33-5-1a: ACK/NACK based HARQ-ACK feedback and RRC-based enabling/disabling ACK/NACK-based feedback
     -- for SPS group-common PDSCH for multicast
   ack-NACK-FeedbackForSPS-Multicast-r17 [12] ENUMERATED { supported(0) }
       OPTIONAL,
     -- R1 33-5-1d: PTP retransmission for SPS group-common PDSCH for multicast
   ptp-Retx-SPS-Multicast-r17 [13] ENUMERATED { supported(0) } OPTIONAL,
     -- R4 26-1: Higher Power Limit CA DC
   higherPowerLimit-r17 [14] ENUMERATED { supported(0) } OPTIONAL,
     -- R1 39-4: Parallel MsgA and SRS/PUCCH/PUSCH transmissions across CCs in intra-band non-contiguous CA
   parallelTxMsgA-SRS-PUCCH-PUSCH-intraBand-r17 [15] ENUMERATED { supported(0)
       } OPTIONAL,
     -- R1 24-11a: Capability on the number of CCs for monitoring a maximum number of BDs and non-overlapped CCEs per span when
     -- configured with DL CA with Rel-17 PDCCH monitoring capability on all the serving cells
   pdcch-MonitoringCA-r17 [16] INTEGER (4..16) OPTIONAL,
     -- R1 24-11f: Capability on the number of CCs for monitoring a maximum number of BDs and non-overlapped CCEs for MCG and for SCG
     -- when configured for NR-DC operation with Rel-17 PDCCH monitoring capability on all the serving cells
   pdcch-BlindDetectionMCG-SCG-List-r17 [17] SEQUENCE (SIZE (1..maxNrofPdcch-BlindDetection-r17)) OF 
      PDCCH-BlindDetectionMCG-SCG-r17 OPTIONAL,
     -- R1 24-11c: Number of carriers for CCE/BD scaling with DL CA with mix of Rel. 17 and Rel. 15 PDCCH monitoring capabilities on
     -- different Carriers
     -- R1 24-11g: Number of carriers for CCE/BD scaling for MCG and for SCG when configured for NR-DC operation with mix of Rel. 17 and
     -- Rel. 15 PDCCH monitoring capabilities on different carriers
   pdcch-BlindDetectionMixedList1-r17 [18] SEQUENCE (SIZE (1..maxNrofPdcch-BlindDetection-r17)) OF 
      PDCCH-BlindDetectionMixed-r17 OPTIONAL,
     -- R1 24-11d: Number of carriers for CCE/BD scaling with DL CA with mix of Rel. 17 and Rel. 16 PDCCH monitoring capabilities on
     -- different Carriers
     -- R1 24-11h: Number of carriers for CCE/BD scaling for MCG and for SCG when configured for NR-DC operation with mix of Rel. 17 and
     -- Rel. 16 PDCCH monitoring capabilities on different carriers
   pdcch-BlindDetectionMixedList2-r17 [19] SEQUENCE (SIZE (1..maxNrofPdcch-BlindDetection-r17)) OF 
      PDCCH-BlindDetectionMixed-r17 OPTIONAL,
     -- R1 24-11e: Number of carriers for CCE/BD scaling with DL CA with mix of Rel. 17, Rel. 16 and Rel. 15 PDCCH monitoring
     -- capabilities on different carriers
     -- R1 24-11i: Number of carriers for CCE/BD scaling for MCG and for SCG when configured for NR-DC operation with mix of Rel. 17,
     -- Rel. 16 and Rel. 15 PDCCH monitoring capabilities on different carriers
   pdcch-BlindDetectionMixedList3-r17 [20] SEQUENCE (SIZE (1..maxNrofPdcch-BlindDetection-r17)) OF 
      PDCCH-BlindDetectionMixed1-r17 OPTIONAL
}

CA-ParametersNRDC-v1720 ::= SEQUENCE {
   ca-ParametersNR-ForDC-v1700 [0] CA-ParametersNR-v1700 OPTIONAL,
   ca-ParametersNR-ForDC-v1720 [1] CA-ParametersNR-v1720 OPTIONAL
}

BandCombination-v1720 ::= SEQUENCE {
   ca-ParametersNR-v1720 [0] CA-ParametersNR-v1720 OPTIONAL,
   ca-ParametersNRDC-v1720 [1] CA-ParametersNRDC-v1720 OPTIONAL
}

BandCombinationList-v1720 ::= SEQUENCE (SIZE (1..maxBandComb)) OF BandCombination-v1720

CA-ParametersNR-v1730 ::= SEQUENCE {
     -- R1 30-4a: DM-RS bundling for PUSCH repetition type A (per BC)
   dmrs-BundlingPUSCH-RepTypeAPerBC-r17 [0] ENUMERATED { supported(0) }
       OPTIONAL,
     -- R1 30-4b: DM-RS bundling for PUSCH repetition type B(per BC)
   dmrs-BundlingPUSCH-RepTypeBPerBC-r17 [1] ENUMERATED { supported(0) }
       OPTIONAL,
     -- R1 30-4c: DM-RS bundling for TB processing over multi-slot PUSCH(per BC)
   dmrs-BundlingPUSCH-multiSlotPerBC-r17 [2] ENUMERATED { supported(0) }
       OPTIONAL,
     -- R1 30-4d: DMRS bundling for PUCCH repetitions(per BC)
   dmrs-BundlingPUCCH-RepPerBC-r17 [3] ENUMERATED { supported(0) } OPTIONAL,
     -- R1 30-4g: Restart DM-RS bundling (per BC)
   dmrs-BundlingRestartPerBC-r17 [4] ENUMERATED { supported(0) } OPTIONAL,
     -- R1 30-4h: DM-RS bundling for non-back-to-back transmission (per BC)
   dmrs-BundlingNonBackToBackTX-PerBC-r17 [5] ENUMERATED { supported(0) }
       OPTIONAL,
     -- R1 39-3-1: Stay on the target CC for SRS carrier switching
   stayOnTargetCC-SRS-CarrierSwitch-r17 [6] ENUMERATED { supported(0) }
       OPTIONAL,
     -- R1 33-3-3a: FDM-ed Type-1 and Type-2 HARQ-ACK codebooks for multiplexing HARQ-ACK for unicast and HARQ-ACK for multicast
   fdm-CodebookForMux-UnicastMulticastHARQ-ACK-r17 [7] ENUMERATED { 
      supported(0) } OPTIONAL,
     -- R1 33-3-3b: Mode 2 TDM-ed Type-1 and Type-2 HARQ-ACK codebook for multiplexing HARQ-ACK for unicast and HARQ-ACK for multicast
   mode2-TDM-CodebookForMux-UnicastMulticastHARQ-ACK-r17 [8] ENUMERATED { 
      supported(0) } OPTIONAL,
     -- R1 33-3-4: Mode 1 for type1 codebook generation
   mode1-ForType1-CodebookGeneration-r17 [9] ENUMERATED { supported(0) }
       OPTIONAL,
     -- R1 33-5-1j: NACK-only based HARQ-ACK feedback for multicast corresponding to a specific sequence or a PUCCH transmission
     -- for SPS group-commmon PDSCH for multicast
   nack-OnlyFeedbackSpecificResourceForSPS-Multicast-r17 [10] ENUMERATED { 
      supported(0) } OPTIONAL,
     -- R1 33-8-2: Up to 2 PUCCH resources configuration for multicast feedback for dynamically scheduled multicast
   multiPUCCH-ConfigForMulticast-r17 [11] ENUMERATED { supported(0) } OPTIONAL,
     -- R1 33-8-3: PUCCH resource configuration for multicast feedback for SPS GC-PDSCH
   pucch-ConfigForSPS-Multicast-r17 [12] ENUMERATED { supported(0) } OPTIONAL,
     -- The following parameter is associated with R1 33-2a, R1 33-3-3a, and R1 33-3-3b, and is not a RAN1 FG.
   maxNumberG-RNTI-HARQ-ACK-Codebook-r17 [13] INTEGER (1..4) OPTIONAL,
     -- R1 33-3-5: Feedback multiplexing for unicast PDSCH and group-common PDSCH for multicast with same priority and different codebook
     -- type
   mux-HARQ-ACK-UnicastMulticast-r17 [14] ENUMERATED { supported(0) } OPTIONAL
}

CA-ParametersNRDC-v1730 ::= SEQUENCE {
   ca-ParametersNR-ForDC-v1730 [0] CA-ParametersNR-v1730 OPTIONAL
}

BandParameters-v1730 ::= SEQUENCE {
     -- R1 39-3-2	Affected bands for inter-band CA during SRS carrier switching
   srs-SwitchingAffectedBandsListNR-r17 [0] SEQUENCE (SIZE (1..maxSimultaneousBands)) OF 
      SRS-SwitchingAffectedBandsNR-r17
}

BandCombination-v1730 ::= SEQUENCE {
   ca-ParametersNR-v1730 [0] CA-ParametersNR-v1730 OPTIONAL,
   ca-ParametersNRDC-v1730 [1] CA-ParametersNRDC-v1730 OPTIONAL,
   bandList-v1730 [2] SEQUENCE (SIZE (1..maxSimultaneousBands)) OF BandParameters-v1730 OPTIONAL
}

BandCombinationList-v1730 ::= SEQUENCE (SIZE (1..maxBandComb)) OF BandCombination-v1730

CA-ParametersNR-v1740 ::= SEQUENCE {
     -- R1 33-5-1f: NACK-only based HARQ-ACK feedback for multicast RRC-based enabling/disabling NACK-only based feedback
     -- for SPS group-common PDSCH for multicast
   nack-OnlyFeedbackForSPS-Multicast-r17 [0] ENUMERATED { supported(0) }
       OPTIONAL,
     -- R1 33-8-1: PUCCH resource configuration for multicast feedback for dynamically scheduled multicast
   singlePUCCH-ConfigForMulticast-r17 [1] ENUMERATED { supported(0) } OPTIONAL
}

BandCombination-v1740 ::= SEQUENCE {
   ca-ParametersNR-v1740 [0] CA-ParametersNR-v1740 OPTIONAL
}

BandCombinationList-v1740 ::= SEQUENCE (SIZE (1..maxBandComb)) OF BandCombination-v1740

CA-ParametersNR-v1760 ::= SEQUENCE {
   prioSCellPRACH-OverSP-PeriodicSRS-Support-r17 [0] ENUMERATED { supported(0)
       } OPTIONAL
}

CA-ParametersNRDC-v1760 ::= SEQUENCE {
   ca-ParametersNR-ForDC-v1760 [0] CA-ParametersNR-v1760
}

BandCombination-v1760 ::= SEQUENCE {
   ca-ParametersNR-v1760 [0] CA-ParametersNR-v1760,
   ca-ParametersNRDC-v1760 [1] CA-ParametersNRDC-v1760
}

BandCombinationList-v1760 ::= SEQUENCE (SIZE (1..maxBandComb)) OF BandCombination-v1760

BandParameters-v1770 ::= SEQUENCE {
   ca-BandwidthClassDL-NR-r17 [0] CA-BandwidthClassNR-r17 OPTIONAL,
   ca-BandwidthClassUL-NR-r17 [1] CA-BandwidthClassNR-r17 OPTIONAL
}

MRDC-Parameters-v1770 ::= SEQUENCE {
     -- R4 26-1: Higher Power Limit CA DC
   higherPowerLimitMRDC-r17 [0] ENUMERATED { supported(0) } OPTIONAL
}

CA-ParametersNR-v1770 ::= SEQUENCE {
   parallelTxPUCCH-PUSCH-SamePriority-r17 [0] ENUMERATED { supported(0) }
       OPTIONAL
}

BandCombination-v1770 ::= SEQUENCE {
   bandList-v1770 [0] SEQUENCE (SIZE (1..maxSimultaneousBands)) OF BandParameters-v1770,
   mrdc-Parameters-v1770 [1] MRDC-Parameters-v1770 OPTIONAL,
   ca-ParametersNR-v1770 [2] CA-ParametersNR-v1770 OPTIONAL
}

BandCombinationList-v1770 ::= SEQUENCE (SIZE (1..maxBandComb)) OF BandCombination-v1770

-- TAG-SRS-SWITCHINGTIMEEUTRA-STOP
-- TAG-SUPPORTEDAGGBANDWIDTH-START
SupportedAggBandwidth-r17 ::= CHOICE {
   fr1-r17 [0] ENUMERATED { mhz20(0), mhz30(1), mhz35(2), mhz40(3), mhz50(4), 
      mhz60(5), mhz70(6), mhz80(7), mhz90(8), mhz100(9), mhz110(10), mhz120(11)
      , mhz130(12), mhz140(13), mhz150(14), mhz160(15), mhz180(16), mhz200(17)
      , mhz220(18), mhz230(19), mhz250(20), mhz280(21), mhz290(22), mhz300(23)
      , mhz350(24), mhz400(25), mhz450(26), mhz500(27), mhz600(28), mhz700(29)
      , mhz800(30), spare1(31) },
   fr2-r17 [1] ENUMERATED { mhz200(0), mhz300(1), mhz400(2), mhz500(3), 
      mhz600(4), mhz700(5), mhz800(6), mhz900(7), mhz1000(8), mhz1100(9), 
      mhz1200(10), mhz1300(11), mhz1400(12), mhz1500(13), mhz1600(14), 
      mhz1700(15), mhz1800(16), mhz1900(17), mhz2000(18), mhz2100(19), 
      mhz2200(20), mhz2300(21), mhz2400(22), spare9(23), spare8(24), spare7(25)
      , spare6(26), spare5(27), spare4(28), spare3(29), spare2(30), spare1(31)
       }
}

CA-ParametersNR-v1780 ::= SEQUENCE {
   parallelTxPUCCH-PUSCH-SamePriority-r17 [0] ENUMERATED { supported(0) }
       OPTIONAL,
   supportedAggBW-FR1-r17 [1] SEQUENCE {
      scalingFactorSCS-r17 [0] ENUMERATED { true(0) } OPTIONAL,
      supportedAggBW-FDD-DL-r17 [1] EXPLICIT SupportedAggBandwidth-r17 OPTIONAL
         ,
      supportedAggBW-FDD-UL-r17 [2] EXPLICIT SupportedAggBandwidth-r17 OPTIONAL
         ,
      supportedAggBW-TDD-DL-r17 [3] EXPLICIT SupportedAggBandwidth-r17 OPTIONAL
         ,
      supportedAggBW-TDD-UL-r17 [4] EXPLICIT SupportedAggBandwidth-r17 OPTIONAL
         ,
      supportedAggBW-TotalDL-r17 [5] EXPLICIT SupportedAggBandwidth-r17
          OPTIONAL,
      supportedAggBW-TotalUL-r17 [6] EXPLICIT SupportedAggBandwidth-r17
          OPTIONAL
   } OPTIONAL
}

CA-ParametersNRDC-v1780 ::= SEQUENCE {
   ca-ParametersNR-ForDC-v1780 [0] CA-ParametersNR-v1780 OPTIONAL
}

BandParameters-v1780 ::= SEQUENCE {
   ca-BandwidthClassDL-NR-r17 [0] CA-BandwidthClassNR-r17 OPTIONAL,
   ca-BandwidthClassUL-NR-r17 [1] CA-BandwidthClassNR-r17 OPTIONAL,
   supportedAggBW-FR2-r17 [2] SEQUENCE {
      supportedAggBW-DL-r17 [0] EXPLICIT SupportedAggBandwidth-r17 OPTIONAL,
      supportedAggBW-UL-r17 [1] EXPLICIT SupportedAggBandwidth-r17 OPTIONAL
   } OPTIONAL
}

BandCombination-v1780 ::= SEQUENCE {
   ca-ParametersNR-v1780 [0] CA-ParametersNR-v1780 OPTIONAL,
   ca-ParametersNRDC-v1780 [1] CA-ParametersNRDC-v1780 OPTIONAL,
   bandList-v1780 [2] SEQUENCE (SIZE (1..maxSimultaneousBands)) OF BandParameters-v1780 OPTIONAL,
   mrdc-Parameters-v1780 [3] MRDC-Parameters-v1770 OPTIONAL
}

BandCombinationList-v1780 ::= SEQUENCE (SIZE (1..maxBandComb)) OF BandCombination-v1780

ULTxSwitchingBandPair-r16 ::= SEQUENCE {
   bandIndexUL1-r16 [0] INTEGER (1..maxSimultaneousBands),
   bandIndexUL2-r16 [1] INTEGER (1..maxSimultaneousBands),
   uplinkTxSwitchingPeriod-r16 [2] ENUMERATED { n35us(0), n140us(1), n210us(2)
       },
   uplinkTxSwitching-DL-Interruption-r16 [3] BIT STRING  (SIZE (1..maxSimultaneousBands)) OPTIONAL
}

BandCombination-UplinkTxSwitch-r16 ::= SEQUENCE {
   bandCombination-r16 [0] BandCombination,
   bandCombination-v1540 [1] BandCombination-v1540 OPTIONAL,
   bandCombination-v1560 [2] BandCombination-v1560 OPTIONAL,
   bandCombination-v1570 [3] BandCombination-v1570 OPTIONAL,
   bandCombination-v1580 [4] BandCombination-v1580 OPTIONAL,
   bandCombination-v1590 [5] BandCombination-v1590 OPTIONAL,
   bandCombination-v1610 [6] BandCombination-v1610 OPTIONAL,
   supportedBandPairListNR-r16 [7] SEQUENCE (SIZE (1..maxULTxSwitchingBandPairs)) OF 
      ULTxSwitchingBandPair-r16,
   uplinkTxSwitching-OptionSupport-r16 [8] ENUMERATED { switchedUL(0), 
      dualUL(1), both(2) } OPTIONAL,
   uplinkTxSwitching-PowerBoosting-r16 [9] ENUMERATED { supported(0) } OPTIONAL
      ,
   ...,
   [[
      uplinkTxSwitching-PUSCH-TransCoherence-r16 [10] ENUMERATED { 
         nonCoherent(0), fullCoherent(1) } OPTIONAL
   ]]
}

BandCombinationList-UplinkTxSwitch-r16 ::= SEQUENCE (SIZE (1..maxBandComb)) OF 
   BandCombination-UplinkTxSwitch-r16

BandCombination-UplinkTxSwitch-v1630 ::= SEQUENCE {
   bandCombination-v1630 [0] BandCombination-v1630 OPTIONAL
}

BandCombinationList-UplinkTxSwitch-v1630 ::= SEQUENCE (SIZE (1..maxBandComb)) OF 
   BandCombination-UplinkTxSwitch-v1630

BandCombination-UplinkTxSwitch-v1640 ::= SEQUENCE {
   bandCombination-v1640 [0] BandCombination-v1640 OPTIONAL
}

BandCombinationList-UplinkTxSwitch-v1640 ::= SEQUENCE (SIZE (1..maxBandComb)) OF 
   BandCombination-UplinkTxSwitch-v1640

BandCombination-UplinkTxSwitch-v1650 ::= SEQUENCE {
   bandCombination-v1650 [0] BandCombination-v1650 OPTIONAL
}

BandCombinationList-UplinkTxSwitch-v1650 ::= SEQUENCE (SIZE (1..maxBandComb)) OF 
   BandCombination-UplinkTxSwitch-v1650

BandCombination-UplinkTxSwitch-v1670 ::= SEQUENCE {
   bandCombination-v15g0 [0] BandCombination-v15g0 OPTIONAL
}

BandCombinationList-UplinkTxSwitch-v1670 ::= SEQUENCE (SIZE (1..maxBandComb)) OF 
   BandCombination-UplinkTxSwitch-v1670

BandCombination-UplinkTxSwitch-v1690 ::= SEQUENCE {
   bandCombination-v1690 [0] BandCombination-v1690 OPTIONAL
}

BandCombinationList-UplinkTxSwitch-v1690 ::= SEQUENCE (SIZE (1..maxBandComb)) OF 
   BandCombination-UplinkTxSwitch-v1690

BandCombination-UplinkTxSwitch-v16a0 ::= SEQUENCE {
   bandCombination-v16a0 [0] BandCombination-v16a0 OPTIONAL
}

BandCombinationList-UplinkTxSwitch-v16a0 ::= SEQUENCE (SIZE (1..maxBandComb)) OF 
   BandCombination-UplinkTxSwitch-v16a0

BandCombination-UplinkTxSwitch-v16e0 ::= SEQUENCE {
   bandCombination-v15n0 [0] BandCombination-v15n0 OPTIONAL
}

BandCombinationList-UplinkTxSwitch-v16e0 ::= SEQUENCE (SIZE (1..maxBandComb)) OF 
   BandCombination-UplinkTxSwitch-v16e0

ULTxSwitchingBandPair-v1700 ::= SEQUENCE {
   uplinkTxSwitchingPeriod2T2T-r17 [0] ENUMERATED { n35us(0), n140us(1), 
      n210us(2) } OPTIONAL
}

UplinkTxSwitchingBandParameters-v1700 ::= SEQUENCE {
   bandIndex-r17 [0] INTEGER (1..maxSimultaneousBands),
   uplinkTxSwitching2T2T-PUSCH-TransCoherence-r17 [1] ENUMERATED { 
      nonCoherent(0), fullCoherent(1) } OPTIONAL
}

BandCombination-UplinkTxSwitch-v1700 ::= SEQUENCE {
   bandCombination-v1700 [0] BandCombination-v1700 OPTIONAL,
     -- R4 16-1/16-2/16-3 Dynamic Tx switching between 2CC/3CC 2Tx-2Tx/1Tx-2Tx switching
   supportedBandPairListNR-v1700 [1] SEQUENCE (SIZE (1..maxULTxSwitchingBandPairs)) OF 
      ULTxSwitchingBandPair-v1700 OPTIONAL,
     -- R4 16-6: UL-MIMO coherence capability for dynamic Tx switching between 2Tx-2Tx switching
   uplinkTxSwitchingBandParametersList-v1700 [2] SEQUENCE (SIZE (1..maxSimultaneousBands)) OF 
      UplinkTxSwitchingBandParameters-v1700 OPTIONAL
}

BandCombinationList-UplinkTxSwitch-v1700 ::= SEQUENCE (SIZE (1..maxBandComb)) OF 
   BandCombination-UplinkTxSwitch-v1700

BandCombination-UplinkTxSwitch-v1720 ::= SEQUENCE {
   bandCombination-v1720 [0] BandCombination-v1720 OPTIONAL,
   uplinkTxSwitching-OptionSupport2T2T-r17 [1] ENUMERATED { switchedUL(0), 
      dualUL(1), both(2) } OPTIONAL
}

BandCombinationList-UplinkTxSwitch-v1720 ::= SEQUENCE (SIZE (1..maxBandComb)) OF 
   BandCombination-UplinkTxSwitch-v1720

BandCombination-UplinkTxSwitch-v1730 ::= SEQUENCE {
   bandCombination-v1730 [0] BandCombination-v1730 OPTIONAL
}

BandCombinationList-UplinkTxSwitch-v1730 ::= SEQUENCE (SIZE (1..maxBandComb)) OF 
   BandCombination-UplinkTxSwitch-v1730

BandCombination-UplinkTxSwitch-v1740 ::= SEQUENCE {
   bandCombination-v1740 [0] BandCombination-v1740 OPTIONAL
}

BandCombinationList-UplinkTxSwitch-v1740 ::= SEQUENCE (SIZE (1..maxBandComb)) OF 
   BandCombination-UplinkTxSwitch-v1740

BandCombination-UplinkTxSwitch-v1760 ::= SEQUENCE {
   bandCombination-v1760 [0] BandCombination-v1760 OPTIONAL
}

BandCombinationList-UplinkTxSwitch-v1760 ::= SEQUENCE (SIZE (1..maxBandComb)) OF 
   BandCombination-UplinkTxSwitch-v1760

BandCombination-UplinkTxSwitch-v1770 ::= SEQUENCE {
   bandCombination-v1770 [0] BandCombination-v1770 OPTIONAL
}

BandCombinationList-UplinkTxSwitch-v1770 ::= SEQUENCE (SIZE (1..maxBandComb)) OF 
   BandCombination-UplinkTxSwitch-v1770

BandCombination-UplinkTxSwitch-v1780 ::= SEQUENCE {
   bandCombination-v1780 [0] BandCombination-v1780 OPTIONAL
}

BandCombinationList-UplinkTxSwitch-v1780 ::= SEQUENCE (SIZE (1..maxBandComb)) OF 
   BandCombination-UplinkTxSwitch-v1780

BandParametersSidelink-r16 ::= SEQUENCE {
   freqBandSidelink-r16 [0] FreqBandIndicatorNR
}

BandParametersSidelinkEUTRA-NR-r16 ::= CHOICE {
   eutra [0] SEQUENCE {
      bandParametersSidelinkEUTRA1-r16 [0] OCTET STRING OPTIONAL,
      bandParametersSidelinkEUTRA2-r16 [1] OCTET STRING OPTIONAL
   },
   nr [1] SEQUENCE {
      bandParametersSidelinkNR-r16 [0] BandParametersSidelink-r16
   }
}

BandCombinationParametersSidelinkEUTRA-NR-r16 ::= SEQUENCE (SIZE (1..maxSimultaneousBands)) OF 
   BandParametersSidelinkEUTRA-NR-r16

-- TAG-BANDCOMBINATIONLIST-STOP
-- TAG-BANDCOMBINATIONLISTSIDELINKEUTRANR-START
BandCombinationListSidelinkEUTRA-NR-r16 ::= SEQUENCE (SIZE (1..maxBandComb)) OF 
   BandCombinationParametersSidelinkEUTRA-NR-r16

BandParametersSidelinkEUTRA-NR-v1630 ::= CHOICE {
   eutra [0] NULL,
   nr [1] SEQUENCE {
      tx-Sidelink-r16 [0] ENUMERATED { supported(0) } OPTIONAL,
      rx-Sidelink-r16 [1] ENUMERATED { supported(0) } OPTIONAL,
      sl-CrossCarrierScheduling-r16 [2] ENUMERATED { supported(0) } OPTIONAL
   }
}

BandCombinationParametersSidelinkEUTRA-NR-v1630 ::= SEQUENCE (SIZE (1..maxSimultaneousBands)) OF 
   BandParametersSidelinkEUTRA-NR-v1630

BandCombinationListSidelinkEUTRA-NR-v1630 ::= SEQUENCE (SIZE (1..maxBandComb)) OF 
   BandCombinationParametersSidelinkEUTRA-NR-v1630

BandParametersSidelinkEUTRA-NR-v1710 ::= CHOICE {
   eutra [0] NULL,
   nr [1] SEQUENCE {
          --32-4
      sl-TransmissionMode2-PartialSensing-r17 [0] SEQUENCE {
         harq-TxProcessModeTwoSidelink-r17 [0] ENUMERATED { n8(0), n16(1) },
         scs-CP-PatternTxSidelinkModeTwo-r17 [1] EXPLICIT CHOICE {
            fr1-r17 [0] SEQUENCE {
               scs-15kHz-r17 [0] BIT STRING  (SIZE (16)) OPTIONAL,
               scs-30kHz-r17 [1] BIT STRING  (SIZE (16)) OPTIONAL,
               scs-60kHz-r17 [2] BIT STRING  (SIZE (16)) OPTIONAL
            },
            fr2-r17 [1] SEQUENCE {
               scs-60kHz-r17 [0] BIT STRING  (SIZE (16)) OPTIONAL,
               scs-120kHz-r17 [1] BIT STRING  (SIZE (16)) OPTIONAL
            }
         } OPTIONAL,
         extendedCP-Mode2PartialSensing-r17 [2] ENUMERATED { supported(0) }
             OPTIONAL,
         dl-openLoopPC-Sidelink-r17 [3] ENUMERATED { supported(0) } OPTIONAL
      } OPTIONAL,
          --32-2a:  Receiving NR sidelink of PSFCH
      rx-sidelinkPSFCH-r17 [1] ENUMERATED { n5(0), n15(1), n25(2), n32(3), 
         n35(4), n45(5), n50(6), n64(7) } OPTIONAL,
          --32-5a-1
      tx-IUC-Scheme1-Mode2Sidelink-r17 [2] ENUMERATED { supported(0) } OPTIONAL
         ,
          --32-5b-1
      tx-IUC-Scheme2-Mode2Sidelink-r17 [3] ENUMERATED { n4(0), n8(1), n16(2) }
          OPTIONAL
   }
}

BandCombinationParametersSidelinkEUTRA-NR-v1710 ::= SEQUENCE (SIZE (1..maxSimultaneousBands)) OF 
   BandParametersSidelinkEUTRA-NR-v1710

BandCombinationListSidelinkEUTRA-NR-v1710 ::= SEQUENCE (SIZE (1..maxBandComb)) OF 
   BandCombinationParametersSidelinkEUTRA-NR-v1710

BandParametersSidelinkDiscovery-r17 ::= SEQUENCE {
   sl-CrossCarrierScheduling-r17 [0] ENUMERATED { supported(0) } OPTIONAL,
     --R1 32-4: Transmitting NR sidelink mode 2 with partial sensing
   sl-TransmissionMode2-PartialSensing-r17 [1] SEQUENCE {
      harq-TxProcessModeTwoSidelink-r17 [0] ENUMERATED { n8(0), n16(1) },
      scs-CP-PatternTxSidelinkModeTwo-r17 [1] EXPLICIT CHOICE {
         fr1-r17 [0] SEQUENCE {
            scs-15kHz-r17 [0] BIT STRING  (SIZE (16)) OPTIONAL,
            scs-30kHz-r17 [1] BIT STRING  (SIZE (16)) OPTIONAL,
            scs-60kHz-r17 [2] BIT STRING  (SIZE (16)) OPTIONAL
         },
         fr2-r17 [1] SEQUENCE {
            scs-60kHz-r17 [0] BIT STRING  (SIZE (16)) OPTIONAL,
            scs-120kHz-r17 [1] BIT STRING  (SIZE (16)) OPTIONAL
         }
      } OPTIONAL,
      extendedCP-Mode2PartialSensing-r17 [2] ENUMERATED { supported(0) }
          OPTIONAL,
      dl-openLoopPC-Sidelink-r17 [3] ENUMERATED { supported(0) } OPTIONAL
   } OPTIONAL,
     --R1 32-5a-1: Transmitting Inter-UE coordination scheme 1 in NR sidelink mode 2
   tx-IUC-Scheme1-Mode2Sidelink-r17 [2] ENUMERATED { supported(0) } OPTIONAL
}

-- TAG-BANDCOMBINATIONLISTSIDELINKEUTRANR-STOP
-- TAG-BANDCOMBINATIONLISTSLDISCOVERY-START
BandCombinationListSL-Discovery-r17 ::= SEQUENCE (SIZE (1..maxSimultaneousBands)) OF 
   BandParametersSidelinkDiscovery-r17

-- TAG-CA-PARAMETERS-NRDC-STOP
-- TAG-CARRIERAGGREGATIONVARIANT-START
CarrierAggregationVariant ::= SEQUENCE {
   fr1fdd-FR1TDD-CA-SpCellOnFR1FDD [0] ENUMERATED { supported(0) } OPTIONAL,
   fr1fdd-FR1TDD-CA-SpCellOnFR1TDD [1] ENUMERATED { supported(0) } OPTIONAL,
   fr1fdd-FR2TDD-CA-SpCellOnFR1FDD [2] ENUMERATED { supported(0) } OPTIONAL,
   fr1fdd-FR2TDD-CA-SpCellOnFR2TDD [3] ENUMERATED { supported(0) } OPTIONAL,
   fr1tdd-FR2TDD-CA-SpCellOnFR1TDD [4] ENUMERATED { supported(0) } OPTIONAL,
   fr1tdd-FR2TDD-CA-SpCellOnFR2TDD [5] ENUMERATED { supported(0) } OPTIONAL,
   fr1fdd-FR1TDD-FR2TDD-CA-SpCellOnFR1FDD [6] ENUMERATED { supported(0) }
       OPTIONAL,
   fr1fdd-FR1TDD-FR2TDD-CA-SpCellOnFR1TDD [7] ENUMERATED { supported(0) }
       OPTIONAL,
   fr1fdd-FR1TDD-FR2TDD-CA-SpCellOnFR2TDD [8] ENUMERATED { supported(0) }
       OPTIONAL
}

SupportedCSI-RS-Resource ::= SEQUENCE {
   maxNumberTxPortsPerResource [0] ENUMERATED { p2(0), p4(1), p8(2), p12(3), 
      p16(4), p24(5), p32(6) },
   maxNumberResourcesPerBand [1] INTEGER (1..64),
   totalNumberTxPortsPerBand [2] INTEGER (2..256)
}

-- TAG-CARRIERAGGREGATIONVARIANT-STOP
-- TAG-CODEBOOKPARAMETERS-START
CodebookParameters ::= SEQUENCE {
   type1 [0] SEQUENCE {
      singlePanel [0] SEQUENCE {
         supportedCSI-RS-ResourceList [0] SEQUENCE (SIZE (1..maxNrofCSI-RS-Resources)) OF 
            SupportedCSI-RS-Resource,
         modes [1] ENUMERATED { mode1(0), mode1andMode2(1) },
         maxNumberCSI-RS-PerResourceSet [2] INTEGER (1..8)
      },
      multiPanel [1] SEQUENCE {
         supportedCSI-RS-ResourceList [0] SEQUENCE (SIZE (1..maxNrofCSI-RS-Resources)) OF 
            SupportedCSI-RS-Resource,
         modes [1] ENUMERATED { mode1(0), mode2(1), both(2) },
         nrofPanels [2] ENUMERATED { n2(0), n4(1) },
         maxNumberCSI-RS-PerResourceSet [3] INTEGER (1..8)
      } OPTIONAL
   },
   type2 [1] SEQUENCE {
      supportedCSI-RS-ResourceList [0] SEQUENCE (SIZE (1..maxNrofCSI-RS-Resources)) OF 
         SupportedCSI-RS-Resource,
      parameterLx [1] INTEGER (2..4),
      amplitudeScalingType [2] ENUMERATED { wideband(0), widebandAndSubband(1)
          },
      amplitudeSubsetRestriction [3] ENUMERATED { supported(0) } OPTIONAL
   } OPTIONAL,
   type2-PortSelection [2] SEQUENCE {
      supportedCSI-RS-ResourceList [0] SEQUENCE (SIZE (1..maxNrofCSI-RS-Resources)) OF 
         SupportedCSI-RS-Resource,
      parameterLx [1] INTEGER (2..4),
      amplitudeScalingType [2] ENUMERATED { wideband(0), widebandAndSubband(1)
          }
   } OPTIONAL
}

CodebookParametersAddition-r16 ::= SEQUENCE {
   etype2-r16 [0] SEQUENCE {
          -- R1 16-3a Regular eType 2 R=1
      etype2R1-r16 [0] SEQUENCE {
         supportedCSI-RS-ResourceListAdd-r16 [0] SEQUENCE (SIZE (1..maxNrofCSI-RS-ResourcesExt-r16)) OF 
            INTEGER (0..maxNrofCSI-RS-ResourcesAlt-1-r16)
      },
          -- R1 16-3a-1 Regular eType 2 R=2
      etype2R2-r16 [1] SEQUENCE {
         supportedCSI-RS-ResourceListAdd-r16 [0] SEQUENCE (SIZE (1..maxNrofCSI-RS-ResourcesExt-r16)) OF 
            INTEGER (0..maxNrofCSI-RS-ResourcesAlt-1-r16)
      } OPTIONAL,
          -- R1 16-3a-2: Support of parameter combinations 7-8
      paramComb7-8-r16 [2] ENUMERATED { supported(0) } OPTIONAL,
          -- R1 16-3a-3: Support of rank 3,4
      rank3-4-r16 [3] ENUMERATED { supported(0) } OPTIONAL,
          -- R1 16-3a-4: CBSR with soft amplitude restriction
      amplitudeSubsetRestriction-r16 [4] ENUMERATED { supported(0) } OPTIONAL
   } OPTIONAL,
   etype2-PS-r16 [1] SEQUENCE {
          -- R1 16-3b Regular eType 2 R=1 PortSelection
      etype2R1-PortSelection-r16 [0] SEQUENCE {
         supportedCSI-RS-ResourceListAdd-r16 [0] SEQUENCE (SIZE (1..maxNrofCSI-RS-ResourcesExt-r16)) OF 
            INTEGER (0..maxNrofCSI-RS-ResourcesAlt-1-r16)
      },
          -- R1 16-3b-1 Regular eType 2 R=2 PortSelection
      etype2R2-PortSelection-r16 [1] SEQUENCE {
         supportedCSI-RS-ResourceListAdd-r16 [0] SEQUENCE (SIZE (1..maxNrofCSI-RS-ResourcesExt-r16)) OF 
            INTEGER (0..maxNrofCSI-RS-ResourcesAlt-1-r16)
      } OPTIONAL,
          -- R1 16-3b-2: Support of rank 3,4
      rank3-4-r16 [2] ENUMERATED { supported(0) } OPTIONAL
   } OPTIONAL
}

CodebookComboParametersAddition-r16 ::= SEQUENCE {
     -- R1 16-8 Mixed codebook types
   type1SP-Type2-null-r16 [0] SEQUENCE {
      supportedCSI-RS-ResourceListAdd-r16 [0] SEQUENCE (SIZE (1..maxNrofCSI-RS-ResourcesExt-r16)) OF INTEGER (0
         ..maxNrofCSI-RS-ResourcesAlt-1-r16)
   } OPTIONAL,
   type1SP-Type2PS-null-r16 [1] SEQUENCE {
      supportedCSI-RS-ResourceListAdd-r16 [0] SEQUENCE (SIZE (1..maxNrofCSI-RS-ResourcesExt-r16)) OF INTEGER (0
         ..maxNrofCSI-RS-ResourcesAlt-1-r16)
   } OPTIONAL,
   type1SP-eType2R1-null-r16 [2] SEQUENCE {
      supportedCSI-RS-ResourceListAdd-r16 [0] SEQUENCE (SIZE (1..maxNrofCSI-RS-ResourcesExt-r16)) OF INTEGER (0
         ..maxNrofCSI-RS-ResourcesAlt-1-r16)
   } OPTIONAL,
   type1SP-eType2R2-null-r16 [3] SEQUENCE {
      supportedCSI-RS-ResourceListAdd-r16 [0] SEQUENCE (SIZE (1..maxNrofCSI-RS-ResourcesExt-r16)) OF INTEGER (0
         ..maxNrofCSI-RS-ResourcesAlt-1-r16)
   } OPTIONAL,
   type1SP-eType2R1PS-null-r16 [4] SEQUENCE {
      supportedCSI-RS-ResourceListAdd-r16 [0] SEQUENCE (SIZE (1..maxNrofCSI-RS-ResourcesExt-r16)) OF INTEGER (0
         ..maxNrofCSI-RS-ResourcesAlt-1-r16)
   } OPTIONAL,
   type1SP-eType2R2PS-null-r16 [5] SEQUENCE {
      supportedCSI-RS-ResourceListAdd-r16 [0] SEQUENCE (SIZE (1..maxNrofCSI-RS-ResourcesExt-r16)) OF INTEGER (0
         ..maxNrofCSI-RS-ResourcesAlt-1-r16)
   } OPTIONAL,
   type1SP-Type2-Type2PS-r16 [6] SEQUENCE {
      supportedCSI-RS-ResourceListAdd-r16 [0] SEQUENCE (SIZE (1..maxNrofCSI-RS-ResourcesExt-r16)) OF INTEGER (0
         ..maxNrofCSI-RS-ResourcesAlt-1-r16)
   } OPTIONAL,
   type1MP-Type2-null-r16 [7] SEQUENCE {
      supportedCSI-RS-ResourceListAdd-r16 [0] SEQUENCE (SIZE (1..maxNrofCSI-RS-ResourcesExt-r16)) OF INTEGER (0
         ..maxNrofCSI-RS-ResourcesAlt-1-r16)
   } OPTIONAL,
   type1MP-Type2PS-null-r16 [8] SEQUENCE {
      supportedCSI-RS-ResourceListAdd-r16 [0] SEQUENCE (SIZE (1..maxNrofCSI-RS-ResourcesExt-r16)) OF INTEGER (0
         ..maxNrofCSI-RS-ResourcesAlt-1-r16)
   } OPTIONAL,
   type1MP-eType2R1-null-r16 [9] SEQUENCE {
      supportedCSI-RS-ResourceListAdd-r16 [0] SEQUENCE (SIZE (1..maxNrofCSI-RS-ResourcesExt-r16)) OF INTEGER (0
         ..maxNrofCSI-RS-ResourcesAlt-1-r16)
   } OPTIONAL,
   type1MP-eType2R2-null-r16 [10] SEQUENCE {
      supportedCSI-RS-ResourceListAdd-r16 [0] SEQUENCE (SIZE (1..maxNrofCSI-RS-ResourcesExt-r16)) OF INTEGER (0
         ..maxNrofCSI-RS-ResourcesAlt-1-r16)
   } OPTIONAL,
   type1MP-eType2R1PS-null-r16 [11] SEQUENCE {
      supportedCSI-RS-ResourceListAdd-r16 [0] SEQUENCE (SIZE (1..maxNrofCSI-RS-ResourcesExt-r16)) OF INTEGER (0
         ..maxNrofCSI-RS-ResourcesAlt-1-r16)
   } OPTIONAL,
   type1MP-eType2R2PS-null-r16 [12] SEQUENCE {
      supportedCSI-RS-ResourceListAdd-r16 [0] SEQUENCE (SIZE (1..maxNrofCSI-RS-ResourcesExt-r16)) OF INTEGER (0
         ..maxNrofCSI-RS-ResourcesAlt-1-r16)
   } OPTIONAL,
   type1MP-Type2-Type2PS-r16 [13] SEQUENCE {
      supportedCSI-RS-ResourceListAdd-r16 [0] SEQUENCE (SIZE (1..maxNrofCSI-RS-ResourcesExt-r16)) OF INTEGER (0
         ..maxNrofCSI-RS-ResourcesAlt-1-r16)
   } OPTIONAL
}

CodebookParametersfetype2-r17 ::= SEQUENCE {
     -- R1 23-9-1  Basic Features of Further Enhanced Port-Selection Type II Codebook (FeType-II)
   fetype2basic-r17 [0] SEQUENCE (SIZE (1..maxNrofCSI-RS-ResourcesExt-r16)) OF INTEGER (0..maxNrofCSI-RS-ResourcesAlt-1-r16),
     -- R1 23-9-2  Support of M=2 and R=1 for FeType-II
   fetype2R1-r17 [1] SEQUENCE (SIZE (1..maxNrofCSI-RS-ResourcesExt-r17)) OF INTEGER (0..maxNrofCSI-RS-ResourcesAlt-1-r16) OPTIONAL,
     -- R1 23-9-4  Support of R = 2 for FeType-II
   fetype2R2-r17 [2] SEQUENCE (SIZE (1..maxNrofCSI-RS-ResourcesExt-r17)) OF INTEGER (0..maxNrofCSI-RS-ResourcesAlt-1-r16) OPTIONAL,
     -- R1 23-9-3  Support of rank 3, 4 for FeType-II
   fetype2Rank3Rank4-r17 [3] ENUMERATED { supported(0) } OPTIONAL
}

CodebookComboParameterMixedType-r17 ::= SEQUENCE {
     -- R1 23-9-5 Active CSI-RS resources and ports for mixed codebook types in any slot
   type1SP-feType2PS-null-r17 [0] SEQUENCE (SIZE (1..maxNrofCSI-RS-ResourcesExt-r16)) OF INTEGER (0..maxNrofCSI-RS-ResourcesAlt-1-r16) OPTIONAL
      ,
   type1SP-feType2PS-M2R1-null-r17 [1] SEQUENCE (SIZE (1..maxNrofCSI-RS-ResourcesExt-r16)) OF INTEGER (0..maxNrofCSI-RS-ResourcesAlt-1-r16)
       OPTIONAL,
   type1SP-feType2PS-M2R2-null-r1 [2] SEQUENCE (SIZE (1..maxNrofCSI-RS-ResourcesExt-r16)) OF INTEGER (0..maxNrofCSI-RS-ResourcesAlt-1-r16)
       OPTIONAL,
   type1SP-Type2-feType2-PS-M1-r17 [3] SEQUENCE (SIZE (1..maxNrofCSI-RS-ResourcesExt-r16)) OF INTEGER (0..maxNrofCSI-RS-ResourcesAlt-1-r16)
       OPTIONAL,
   type1SP-Type2-feType2-PS-M2R1-r17 [4] SEQUENCE (SIZE (1..maxNrofCSI-RS-ResourcesExt-r16)) OF INTEGER (0..maxNrofCSI-RS-ResourcesAlt-1-r16)
       OPTIONAL,
   type1SP-eType2R1-feType2-PS-M1-r17 [5] SEQUENCE (SIZE (1..maxNrofCSI-RS-ResourcesExt-r16)) OF INTEGER (0..maxNrofCSI-RS-ResourcesAlt-1-r16)
       OPTIONAL,
   type1SP-eType2R1-feType2-PS-M2R1-r17 [6] SEQUENCE (SIZE (1..maxNrofCSI-RS-ResourcesExt-r16)) OF INTEGER (0..maxNrofCSI-RS-ResourcesAlt-1-r16
      ) OPTIONAL,
   type1MP-feType2PS-null-r17 [7] SEQUENCE (SIZE (1..maxNrofCSI-RS-ResourcesExt-r16)) OF INTEGER (0..maxNrofCSI-RS-ResourcesAlt-1-r16) OPTIONAL
      ,
   type1MP-feType2PS-M2R1-null-r17 [8] SEQUENCE (SIZE (1..maxNrofCSI-RS-ResourcesExt-r16)) OF INTEGER (0..maxNrofCSI-RS-ResourcesAlt-1-r16)
       OPTIONAL,
   type1MP-feType2PS-M2R2-null-r17 [9] SEQUENCE (SIZE (1..maxNrofCSI-RS-ResourcesExt-r16)) OF INTEGER (0..maxNrofCSI-RS-ResourcesAlt-1-r16)
       OPTIONAL,
   type1MP-Type2-feType2-PS-M1-r17 [10] SEQUENCE (SIZE (1..maxNrofCSI-RS-ResourcesExt-r16)) OF INTEGER (0..maxNrofCSI-RS-ResourcesAlt-1-r16)
       OPTIONAL,
   type1MP-Type2-feType2-PS-M2R1-r17 [11] SEQUENCE (SIZE (1..maxNrofCSI-RS-ResourcesExt-r16)) OF INTEGER (0..maxNrofCSI-RS-ResourcesAlt-1-r16)
       OPTIONAL,
   type1MP-eType2R1-feType2-PS-M1-r17 [12] SEQUENCE (SIZE (1..maxNrofCSI-RS-ResourcesExt-r16)) OF INTEGER (0..maxNrofCSI-RS-ResourcesAlt-1-r16)
       OPTIONAL,
   type1MP-eType2R1-feType2-PS-M2R1-r17 [13] SEQUENCE (SIZE (1..maxNrofCSI-RS-ResourcesExt-r16)) OF INTEGER (0
      ..maxNrofCSI-RS-ResourcesAlt-1-r16) OPTIONAL
}

CodebookComboParameterMultiTRP-r17 ::= SEQUENCE {
     -- R1 23-7-1b	Active CSI-RS resources and ports in the presence of multi-TRP CSI
     --  {Codebook 2, Codebook 3} =(NULL, NULL}
   nCJT-null-null [0] SEQUENCE (SIZE (1..maxNrofCSI-RS-ResourcesExt-r16)) OF INTEGER (0..maxNrofCSI-RS-ResourcesAlt-1-r16) OPTIONAL,
   nCJT1SP-null-null [1] SEQUENCE (SIZE (1..maxNrofCSI-RS-ResourcesExt-r16)) OF INTEGER (0..maxNrofCSI-RS-ResourcesAlt-1-r16) OPTIONAL,
     --    {Codebook 2, Codebook 3} = {( {"Rel 16 combinations in FG 16-8"}
   nCJT-Type2-null-r16 [2] SEQUENCE (SIZE (1..maxNrofCSI-RS-ResourcesExt-r16)) OF INTEGER (0..maxNrofCSI-RS-ResourcesAlt-1-r16) OPTIONAL,
   nCJT-Type2PS-null-r16 [3] SEQUENCE (SIZE (1..maxNrofCSI-RS-ResourcesExt-r16)) OF INTEGER (0..maxNrofCSI-RS-ResourcesAlt-1-r16) OPTIONAL,
   nCJT-eType2R1-null-r16 [4] SEQUENCE (SIZE (1..maxNrofCSI-RS-ResourcesExt-r16)) OF INTEGER (0..maxNrofCSI-RS-ResourcesAlt-1-r16) OPTIONAL,
   nCJT-eType2R2-null-r16 [5] SEQUENCE (SIZE (1..maxNrofCSI-RS-ResourcesExt-r16)) OF INTEGER (0..maxNrofCSI-RS-ResourcesAlt-1-r16) OPTIONAL,
   nCJT-eType2R1PS-null-r16 [6] SEQUENCE (SIZE (1..maxNrofCSI-RS-ResourcesExt-r16)) OF INTEGER (0..maxNrofCSI-RS-ResourcesAlt-1-r16) OPTIONAL,
   nCJT-eType2R2PS-null-r16 [7] SEQUENCE (SIZE (1..maxNrofCSI-RS-ResourcesExt-r16)) OF INTEGER (0..maxNrofCSI-RS-ResourcesAlt-1-r16) OPTIONAL,
   nCJT-Type2-Type2PS-r16 [8] SEQUENCE (SIZE (1..maxNrofCSI-RS-ResourcesExt-r16)) OF INTEGER (0..maxNrofCSI-RS-ResourcesAlt-1-r16) OPTIONAL,
   nCJT1SP-Type2-null-r16 [9] SEQUENCE (SIZE (1..maxNrofCSI-RS-ResourcesExt-r16)) OF INTEGER (0..maxNrofCSI-RS-ResourcesAlt-1-r16) OPTIONAL,
   nCJT1SP-Type2PS-null-r16 [10] SEQUENCE (SIZE (1..maxNrofCSI-RS-ResourcesExt-r16)) OF INTEGER (0..maxNrofCSI-RS-ResourcesAlt-1-r16) OPTIONAL,
   nCJT1SP-eType2R1-null-r16 [11] SEQUENCE (SIZE (1..maxNrofCSI-RS-ResourcesExt-r16)) OF INTEGER (0..maxNrofCSI-RS-ResourcesAlt-1-r16) OPTIONAL
      ,
   nCJT1SP-eType2R2-null-r16 [12] SEQUENCE (SIZE (1..maxNrofCSI-RS-ResourcesExt-r16)) OF INTEGER (0..maxNrofCSI-RS-ResourcesAlt-1-r16) OPTIONAL
      ,
   nCJT1SP-eType2R1PS-null-r16 [13] SEQUENCE (SIZE (1..maxNrofCSI-RS-ResourcesExt-r16)) OF INTEGER (0..maxNrofCSI-RS-ResourcesAlt-1-r16)
       OPTIONAL,
   nCJT1SP-eType2R2PS-null-r16 [14] SEQUENCE (SIZE (1..maxNrofCSI-RS-ResourcesExt-r16)) OF INTEGER (0..maxNrofCSI-RS-ResourcesAlt-1-r16)
       OPTIONAL,
   nCJT1SP-Type2-Type2PS-r16 [15] SEQUENCE (SIZE (1..maxNrofCSI-RS-ResourcesExt-r16)) OF INTEGER (0..maxNrofCSI-RS-ResourcesAlt-1-r16) OPTIONAL
      ,
     -- {Codebook 2, Codebook 3} = {"New Rel17 combinations in FG 23-9-5"}
   nCJT-feType2PS-null-r17 [16] SEQUENCE (SIZE (1..maxNrofCSI-RS-ResourcesExt-r16)) OF INTEGER (0..maxNrofCSI-RS-ResourcesAlt-1-r16) OPTIONAL,
   nCJT-feType2PS-M2R1-null-r17 [17] SEQUENCE (SIZE (1..maxNrofCSI-RS-ResourcesExt-r16)) OF INTEGER (0..maxNrofCSI-RS-ResourcesAlt-1-r16)
       OPTIONAL,
   nCJT-feType2PS-M2R2-null-r17 [18] SEQUENCE (SIZE (1..maxNrofCSI-RS-ResourcesExt-r16)) OF INTEGER (0..maxNrofCSI-RS-ResourcesAlt-1-r16)
       OPTIONAL,
   nCJT-Type2-feType2-PS-M1-r17 [19] SEQUENCE (SIZE (1..maxNrofCSI-RS-ResourcesExt-r16)) OF INTEGER (0..maxNrofCSI-RS-ResourcesAlt-1-r16)
       OPTIONAL,
   nCJT-Type2-feType2-PS-M2R1-r17 [20] SEQUENCE (SIZE (1..maxNrofCSI-RS-ResourcesExt-r16)) OF INTEGER (0..maxNrofCSI-RS-ResourcesAlt-1-r16)
       OPTIONAL,
   nCJT-eType2R1-feType2-PS-M1-r17 [21] SEQUENCE (SIZE (1..maxNrofCSI-RS-ResourcesExt-r16)) OF INTEGER (0..maxNrofCSI-RS-ResourcesAlt-1-r16)
       OPTIONAL,
   nCJT-eType2R1-feType2-PS-M2R1-r17 [22] SEQUENCE (SIZE (1..maxNrofCSI-RS-ResourcesExt-r16)) OF INTEGER (0..maxNrofCSI-RS-ResourcesAlt-1-r16)
       OPTIONAL,
   nCJT1SP-feType2PS-null-r17 [23] SEQUENCE (SIZE (1..maxNrofCSI-RS-ResourcesExt-r16)) OF INTEGER (0..maxNrofCSI-RS-ResourcesAlt-1-r16)
       OPTIONAL,
   nCJT1SP-feType2PS-M2R1-null-r17 [24] SEQUENCE (SIZE (1..maxNrofCSI-RS-ResourcesExt-r16)) OF INTEGER (0..maxNrofCSI-RS-ResourcesAlt-1-r16)
       OPTIONAL,
   nCJT1SP-feType2PS-M2R2-null-r1 [25] SEQUENCE (SIZE (1..maxNrofCSI-RS-ResourcesExt-r16)) OF INTEGER (0..maxNrofCSI-RS-ResourcesAlt-1-r16)
       OPTIONAL,
   nCJT1SP-Type2-feType2-PS-M1-r17 [26] SEQUENCE (SIZE (1..maxNrofCSI-RS-ResourcesExt-r16)) OF INTEGER (0..maxNrofCSI-RS-ResourcesAlt-1-r16)
       OPTIONAL,
   nCJT1SP-Type2-feType2-PS-M2R1-r17 [27] SEQUENCE (SIZE (1..maxNrofCSI-RS-ResourcesExt-r16)) OF INTEGER (0..maxNrofCSI-RS-ResourcesAlt-1-r16)
       OPTIONAL,
   nCJT1SP-eType2R1-feType2-PS-M1-r17 [28] SEQUENCE (SIZE (1..maxNrofCSI-RS-ResourcesExt-r16)) OF INTEGER (0..maxNrofCSI-RS-ResourcesAlt-1-r16)
       OPTIONAL,
   nCJT1SP-eType2R1-feType2-PS-M2R1-r17 [29] SEQUENCE (SIZE (1..maxNrofCSI-RS-ResourcesExt-r16)) OF INTEGER (0
      ..maxNrofCSI-RS-ResourcesAlt-1-r16) OPTIONAL
}

CodebookVariantsList-r16 ::= SEQUENCE (SIZE (1..maxNrofCSI-RS-ResourcesAlt-r16)) OF SupportedCSI-RS-Resource

FeatureSet ::= CHOICE {
   eutra [0] SEQUENCE {
      downlinkSetEUTRA [0] FeatureSetEUTRA-DownlinkId,
      uplinkSetEUTRA [1] FeatureSetEUTRA-UplinkId
   },
   nr [1] SEQUENCE {
      downlinkSetNR [0] FeatureSetDownlinkId,
      uplinkSetNR [1] FeatureSetUplinkId
   }
}

FeatureSetsPerBand ::= SEQUENCE (SIZE (1..maxFeatureSetsPerBand)) OF FeatureSet

-- TAG-CODEBOOKPARAMETERS-STOP
-- TAG-FEATURESETCOMBINATION-START
FeatureSetCombination ::= SEQUENCE (SIZE (1..maxSimultaneousBands)) OF FeatureSetsPerBand

DummyA ::= SEQUENCE {
   maxNumberNZP-CSI-RS-PerCC [0] INTEGER (1..32),
   maxNumberPortsAcrossNZP-CSI-RS-PerCC [1] ENUMERATED { p2(0), p4(1), p8(2), 
      p12(3), p16(4), p24(5), p32(6), p40(7), p48(8), p56(9), p64(10), p72(11)
      , p80(12), p88(13), p96(14), p104(15), p112(16), p120(17), p128(18), 
      p136(19), p144(20), p152(21), p160(22), p168(23), p176(24), p184(25), 
      p192(26), p200(27), p208(28), p216(29), p224(30), p232(31), p240(32), 
      p248(33), p256(34) },
   maxNumberCS-IM-PerCC [2] ENUMERATED { n1(0), n2(1), n4(2), n8(3), n16(4), 
      n32(5) },
   maxNumberSimultaneousCSI-RS-ActBWP-AllCC [3] ENUMERATED { n5(0), n6(1), 
      n7(2), n8(3), n9(4), n10(5), n12(6), n14(7), n16(8), n18(9), n20(10), 
      n22(11), n24(12), n26(13), n28(14), n30(15), n32(16), n34(17), n36(18), 
      n38(19), n40(20), n42(21), n44(22), n46(23), n48(24), n50(25), n52(26), 
      n54(27), n56(28), n58(29), n60(30), n62(31), n64(32) },
   totalNumberPortsSimultaneousCSI-RS-ActBWP-AllCC [4] ENUMERATED { p8(0), 
      p12(1), p16(2), p24(3), p32(4), p40(5), p48(6), p56(7), p64(8), p72(9), 
      p80(10), p88(11), p96(12), p104(13), p112(14), p120(15), p128(16), 
      p136(17), p144(18), p152(19), p160(20), p168(21), p176(22), p184(23), 
      p192(24), p200(25), p208(26), p216(27), p224(28), p232(29), p240(30), 
      p248(31), p256(32) }
}

DummyB ::= SEQUENCE {
   maxNumberTxPortsPerResource [0] ENUMERATED { p2(0), p4(1), p8(2), p12(3), 
      p16(4), p24(5), p32(6) },
   maxNumberResources [1] INTEGER (1..64),
   totalNumberTxPorts [2] INTEGER (2..256),
   supportedCodebookMode [3] ENUMERATED { mode1(0), mode1AndMode2(1) },
   maxNumberCSI-RS-PerResourceSet [4] INTEGER (1..8)
}

DummyC ::= SEQUENCE {
   maxNumberTxPortsPerResource [0] ENUMERATED { p8(0), p16(1), p32(2) },
   maxNumberResources [1] INTEGER (1..64),
   totalNumberTxPorts [2] INTEGER (2..256),
   supportedCodebookMode [3] ENUMERATED { mode1(0), mode2(1), both(2) },
   supportedNumberPanels [4] ENUMERATED { n2(0), n4(1) },
   maxNumberCSI-RS-PerResourceSet [5] INTEGER (1..8)
}

DummyD ::= SEQUENCE {
   maxNumberTxPortsPerResource [0] ENUMERATED { p4(0), p8(1), p12(2), p16(3), 
      p24(4), p32(5) },
   maxNumberResources [1] INTEGER (1..64),
   totalNumberTxPorts [2] INTEGER (2..256),
   parameterLx [3] INTEGER (2..4),
   amplitudeScalingType [4] ENUMERATED { wideband(0), widebandAndSubband(1) },
   amplitudeSubsetRestriction [5] ENUMERATED { supported(0) } OPTIONAL,
   maxNumberCSI-RS-PerResourceSet [6] INTEGER (1..8)
}

DummyE ::= SEQUENCE {
   maxNumberTxPortsPerResource [0] ENUMERATED { p4(0), p8(1), p12(2), p16(3), 
      p24(4), p32(5) },
   maxNumberResources [1] INTEGER (1..64),
   totalNumberTxPorts [2] INTEGER (2..256),
   parameterLx [3] INTEGER (2..4),
   amplitudeScalingType [4] ENUMERATED { wideband(0), widebandAndSubband(1) },
   maxNumberCSI-RS-PerResourceSet [5] INTEGER (1..8)
}

-- TAG-FEATURESETCOMBINATIONID-STOP
-- TAG-FEATURESETDOWNLINK-START
FeatureSetDownlink ::= SEQUENCE {
   featureSetListPerDownlinkCC [0] SEQUENCE (SIZE (1..maxNrofServingCells)) OF 
      FeatureSetDownlinkPerCC-Id,
   intraBandFreqSeparationDL [1] FreqSeparationClass OPTIONAL,
   scalingFactor [2] ENUMERATED { f0p4(0), f0p75(1), f0p8(2) } OPTIONAL,
   dummy8 [3] ENUMERATED { supported(0) } OPTIONAL,
   scellWithoutSSB [4] ENUMERATED { supported(0) } OPTIONAL,
   csi-RS-MeasSCellWithoutSSB [5] ENUMERATED { supported(0) } OPTIONAL,
   dummy1 [6] ENUMERATED { supported(0) } OPTIONAL,
   type1-3-CSS [7] ENUMERATED { supported(0) } OPTIONAL,
   pdcch-MonitoringAnyOccasions [8] ENUMERATED { withoutDCI-Gap(0), 
      withDCI-Gap(1) } OPTIONAL,
   dummy2 [9] ENUMERATED { supported(0) } OPTIONAL,
   ue-SpecificUL-DL-Assignment [10] ENUMERATED { supported(0) } OPTIONAL,
   searchSpaceSharingCA-DL [11] ENUMERATED { supported(0) } OPTIONAL,
   timeDurationForQCL [12] SEQUENCE {
      scs-60kHz [0] ENUMERATED { s7(0), s14(1), s28(2) } OPTIONAL,
      scs-120kHz [1] ENUMERATED { s14(0), s28(1) } OPTIONAL
   } OPTIONAL,
   pdsch-ProcessingType1-DifferentTB-PerSlot [13] SEQUENCE {
      scs-15kHz [0] ENUMERATED { upto2(0), upto4(1), upto7(2) } OPTIONAL,
      scs-30kHz [1] ENUMERATED { upto2(0), upto4(1), upto7(2) } OPTIONAL,
      scs-60kHz [2] ENUMERATED { upto2(0), upto4(1), upto7(2) } OPTIONAL,
      scs-120kHz [3] ENUMERATED { upto2(0), upto4(1), upto7(2) } OPTIONAL
   } OPTIONAL,
   dummy3 [14] DummyA OPTIONAL,
   dummy4 [15] SEQUENCE (SIZE (1..maxNrofCodebooks)) OF DummyB OPTIONAL,
   dummy5 [16] SEQUENCE (SIZE (1..maxNrofCodebooks)) OF DummyC OPTIONAL,
   dummy6 [17] SEQUENCE (SIZE (1..maxNrofCodebooks)) OF DummyD OPTIONAL,
   dummy7 [18] SEQUENCE (SIZE (1..maxNrofCodebooks)) OF DummyE OPTIONAL
}

-- TAG-POWSAV-PARAMETERS-STOP
-- TAG-PROCESSINGPARAMETERS-START
ProcessingParameters ::= SEQUENCE {
   fallback [0] ENUMERATED { sc(0), cap1-only(1) },
   differentTB-PerSlot [1] SEQUENCE {
      upto1 [0] NumberOfCarriers OPTIONAL,
      upto2 [1] NumberOfCarriers OPTIONAL,
      upto4 [2] NumberOfCarriers OPTIONAL,
      upto7 [3] NumberOfCarriers OPTIONAL
   } OPTIONAL
}

FeatureSetDownlink-v1540 ::= SEQUENCE {
   oneFL-DMRS-TwoAdditionalDMRS-DL [0] ENUMERATED { supported(0) } OPTIONAL,
   additionalDMRS-DL-Alt [1] ENUMERATED { supported(0) } OPTIONAL,
   twoFL-DMRS-TwoAdditionalDMRS-DL [2] ENUMERATED { supported(0) } OPTIONAL,
   oneFL-DMRS-ThreeAdditionalDMRS-DL [3] ENUMERATED { supported(0) } OPTIONAL,
   pdcch-MonitoringAnyOccasionsWithSpanGap [4] SEQUENCE {
      scs-15kHz [0] ENUMERATED { set1(0), set2(1), set3(2) } OPTIONAL,
      scs-30kHz [1] ENUMERATED { set1(0), set2(1), set3(2) } OPTIONAL,
      scs-60kHz [2] ENUMERATED { set1(0), set2(1), set3(2) } OPTIONAL,
      scs-120kHz [3] ENUMERATED { set1(0), set2(1), set3(2) } OPTIONAL
   } OPTIONAL,
   pdsch-SeparationWithGap [5] ENUMERATED { supported(0) } OPTIONAL,
   pdsch-ProcessingType2 [6] SEQUENCE {
      scs-15kHz [0] ProcessingParameters OPTIONAL,
      scs-30kHz [1] ProcessingParameters OPTIONAL,
      scs-60kHz [2] ProcessingParameters OPTIONAL
   } OPTIONAL,
   pdsch-ProcessingType2-Limited [7] SEQUENCE {
      differentTB-PerSlot-SCS-30kHz [0] ENUMERATED { upto1(0), upto2(1), 
         upto4(2), upto7(3) }
   } OPTIONAL,
   dl-MCS-TableAlt-DynamicIndication [8] ENUMERATED { supported(0) } OPTIONAL
}

SRS-Resources ::= SEQUENCE {
   maxNumberAperiodicSRS-PerBWP [0] ENUMERATED { n1(0), n2(1), n4(2), n8(3), 
      n16(4) },
   maxNumberAperiodicSRS-PerBWP-PerSlot [1] INTEGER (1..6),
   maxNumberPeriodicSRS-PerBWP [2] ENUMERATED { n1(0), n2(1), n4(2), n8(3), 
      n16(4) },
   maxNumberPeriodicSRS-PerBWP-PerSlot [3] INTEGER (1..6),
   maxNumberSemiPersistentSRS-PerBWP [4] ENUMERATED { n1(0), n2(1), n4(2), 
      n8(3), n16(4) },
   maxNumberSemiPersistentSRS-PerBWP-PerSlot [5] INTEGER (1..6),
   maxNumberSRS-Ports-PerResource [6] ENUMERATED { n1(0), n2(1), n4(2) }
}

FeatureSetDownlink-v15a0 ::= SEQUENCE {
   supportedSRS-Resources [0] SRS-Resources OPTIONAL
}

PDCCH-MonitoringOccasions-r16 ::= SEQUENCE {
   period7span3-r16 [0] ENUMERATED { supported(0) } OPTIONAL,
   period4span3-r16 [1] ENUMERATED { supported(0) } OPTIONAL,
   period2span2-r16 [2] ENUMERATED { supported(0) } OPTIONAL
}

FeatureSetDownlink-v1610 ::= SEQUENCE {
     -- R1 22-4e/4f/4g/4h: CBG based reception for DL with unicast PDSCH(s) per slot per CC with UE processing time Capability 1
   cbgPDSCH-ProcessingType1-DifferentTB-PerSlot-r16 [0] SEQUENCE {
      scs-15kHz-r16 [0] ENUMERATED { one(0), upto2(1), upto4(2), upto7(3) }
          OPTIONAL,
      scs-30kHz-r16 [1] ENUMERATED { one(0), upto2(1), upto4(2), upto7(3) }
          OPTIONAL,
      scs-60kHz-r16 [2] ENUMERATED { one(0), upto2(1), upto4(2), upto7(3) }
          OPTIONAL,
      scs-120kHz-r16 [3] ENUMERATED { one(0), upto2(1), upto4(2), upto7(3) }
          OPTIONAL
   } OPTIONAL,
     -- R1 22-3e/3f/3g/3h: CBG based reception for DL with unicast PDSCH(s) per slot per CC with UE processing time Capability 2
   cbgPDSCH-ProcessingType2-DifferentTB-PerSlot-r16 [1] SEQUENCE {
      scs-15kHz-r16 [0] ENUMERATED { one(0), upto2(1), upto4(2), upto7(3) }
          OPTIONAL,
      scs-30kHz-r16 [1] ENUMERATED { one(0), upto2(1), upto4(2), upto7(3) }
          OPTIONAL,
      scs-60kHz-r16 [2] ENUMERATED { one(0), upto2(1), upto4(2), upto7(3) }
          OPTIONAL,
      scs-120kHz-r16 [3] ENUMERATED { one(0), upto2(1), upto4(2), upto7(3) }
          OPTIONAL
   } OPTIONAL,
   intraFreqDAPS-r16 [2] SEQUENCE {
      intraFreqDiffSCS-DAPS-r16 [0] ENUMERATED { supported(0) } OPTIONAL,
      intraFreqAsyncDAPS-r16 [1] ENUMERATED { supported(0) } OPTIONAL
   } OPTIONAL,
   intraBandFreqSeparationDL-v1620 [3] FreqSeparationClassDL-v1620 OPTIONAL,
   intraBandFreqSeparationDL-Only-r16 [4] FreqSeparationClassDL-Only-r16
       OPTIONAL,
     -- R1 11-2: Rel-16 PDCCH monitoring capability
   pdcch-Monitoring-r16 [5] SEQUENCE {
      pdsch-ProcessingType1-r16 [0] SEQUENCE {
         scs-15kHz-r16 [0] PDCCH-MonitoringOccasions-r16 OPTIONAL,
         scs-30kHz-r16 [1] PDCCH-MonitoringOccasions-r16 OPTIONAL
      } OPTIONAL,
      pdsch-ProcessingType2-r16 [1] SEQUENCE {
         scs-15kHz-r16 [0] PDCCH-MonitoringOccasions-r16 OPTIONAL,
         scs-30kHz-r16 [1] PDCCH-MonitoringOccasions-r16 OPTIONAL
      } OPTIONAL
   } OPTIONAL,
     -- R1 11-2b: Mix of Rel. 16 PDCCH monitoring capability and Rel. 15 PDCCH monitoring capability on different carriers
   pdcch-MonitoringMixed-r16 [6] ENUMERATED { supported(0) } OPTIONAL,
     -- R1 18-5c: Processing up to X unicast DCI scheduling for DL per scheduled CC
   crossCarrierSchedulingProcessing-DiffSCS-r16 [7] SEQUENCE {
      scs-15kHz-120kHz-r16 [0] ENUMERATED { n1(0), n2(1), n4(2) } OPTIONAL,
      scs-15kHz-60kHz-r16 [1] ENUMERATED { n1(0), n2(1), n4(2) } OPTIONAL,
      scs-30kHz-120kHz-r16 [2] ENUMERATED { n1(0), n2(1), n4(2) } OPTIONAL,
      scs-15kHz-30kHz-r16 [3] ENUMERATED { n2(0) } OPTIONAL,
      scs-30kHz-60kHz-r16 [4] ENUMERATED { n2(0) } OPTIONAL,
      scs-60kHz-120kHz-r16 [5] ENUMERATED { n2(0) } OPTIONAL
   } OPTIONAL,
     -- R1 16-2b-1: Support of single-DCI based SDM scheme
   singleDCI-SDM-scheme-r16 [8] ENUMERATED { supported(0) } OPTIONAL
}

PDCCH-RepetitionParameters-r17 ::= SEQUENCE {
   supportedMode-r17 [0] ENUMERATED { intra-span(0), inter-span(1), both(2) },
   limitX-PerCC-r17 [1] ENUMERATED { n4(0), n8(1), n16(2), n32(3), n44(4), 
      n64(5), nolimit(6) } OPTIONAL,
   limitX-AcrossCC-r17 [2] ENUMERATED { n4(0), n8(1), n16(2), n32(3), n44(4), 
      n64(5), n128(6), n256(7), n512(8), nolimit(9) } OPTIONAL
}

FeatureSetDownlink-v1700 ::= SEQUENCE {
     -- R1 36-2: Scaling factor to be applied to 1024QAM for FR1
   scalingFactor-1024QAM-FR1-r17 [0] ENUMERATED { f0p4(0), f0p75(1), f0p8(2) }
       OPTIONAL,
     -- R1 24 feature for existing UE cap to include new SCS
   timeDurationForQCL-v1710 [1] SEQUENCE {
      scs-480kHz [0] ENUMERATED { s56(0), s112(1) } OPTIONAL,
      scs-960kHz [1] ENUMERATED { s112(0), s224(1) } OPTIONAL
   } OPTIONAL,
     -- R1 23-6-1	SFN scheme A (scheme 1) for PDSCH and PDCCH
   sfn-SchemeA-r17 [2] ENUMERATED { supported(0) } OPTIONAL,
     -- R1 23-6-1-1	SFN scheme A (scheme 1) for PDCCH only
   sfn-SchemeA-PDCCH-only-r17 [3] ENUMERATED { supported(0) } OPTIONAL,
     -- R1 23-6-1a	Dynamic switching - scheme A
   sfn-SchemeA-DynamicSwitching-r17 [4] ENUMERATED { supported(0) } OPTIONAL,
     -- R1 23-6-1b	SFN scheme A (scheme 1) for PDSCH only
   sfn-SchemeA-PDSCH-only-r17 [5] ENUMERATED { supported(0) } OPTIONAL,
     -- R1 23-6-2	SFN scheme B (TRP based pre-compensation) for PDSCH and PDCCH
   sfn-SchemeB-r17 [6] ENUMERATED { supported(0) } OPTIONAL,
     -- R1 23-6-2a	Dynamic switching - scheme B
   sfn-SchemeB-DynamicSwitching-r17 [7] ENUMERATED { supported(0) } OPTIONAL,
     -- R1 23-6-2b	SFN scheme B (TRP based pre-compensation) for PDSCH only
   sfn-SchemeB-PDSCH-only-r17 [8] ENUMERATED { supported(0) } OPTIONAL,
     -- R1 23-2-1d	PDCCH repetition for Case 2 PDCCH monitoring with a span gap
   mTRP-PDCCH-Case2-1SpanGap-r17 [9] SEQUENCE {
      scs-15kHz-r17 [0] PDCCH-RepetitionParameters-r17 OPTIONAL,
      scs-30kHz-r17 [1] PDCCH-RepetitionParameters-r17 OPTIONAL,
      scs-60kHz-r17 [2] PDCCH-RepetitionParameters-r17 OPTIONAL,
      scs-120kHz-r17 [3] PDCCH-RepetitionParameters-r17 OPTIONAL
   } OPTIONAL,
     -- R1 23-2-1e	PDCCH repetition for Rel-16 PDCCH monitoring
   mTRP-PDCCH-legacyMonitoring-r17 [10] SEQUENCE {
      scs-15kHz-r17 [0] PDCCH-RepetitionParameters-r17 OPTIONAL,
      scs-30kHz-r17 [1] PDCCH-RepetitionParameters-r17 OPTIONAL
   } OPTIONAL,
     -- R1  23-2-4	Simultaneous configuration of PDCCH repetition and multi-DCI based multi-TRP
   mTRP-PDCCH-multiDCI-multiTRP-r17 [11] ENUMERATED { supported(0) } OPTIONAL,
     -- R1 33-2:	Dynamic scheduling for multicast for PCell
   dynamicMulticastPCell-r17 [12] ENUMERATED { supported(0) } OPTIONAL,
     -- R1 23-2-1	PDCCH repetition
   mTRP-PDCCH-Repetition-r17 [13] SEQUENCE {
      numBD-twoPDCCH-r17 [0] INTEGER (2..3),
      maxNumOverlaps-r17 [1] ENUMERATED { n1(0), n2(1), n3(2), n5(3), n10(4), 
         n20(5), n40(6) }
   } OPTIONAL
}

FeatureSetDownlink-v1720 ::= SEQUENCE {
     -- R1 25-19: RTT-based Propagation delay compensation based on CSI-RS for tracking and SRS
   rtt-BasedPDC-CSI-RS-ForTracking-r17 [0] ENUMERATED { supported(0) } OPTIONAL
      ,
     -- R1 25-19a: RTT-based Propagation delay compensation based on DL PRS for RTT-based PDC and SRS
   rtt-BasedPDC-PRS-r17 [1] SEQUENCE {
      maxNumberPRS-Resource-r17 [0] ENUMERATED { n1(0), n2(1), n4(2), n8(3), 
         n16(4), n32(5), n64(6) },
      maxNumberPRS-ResourceProcessedPerSlot-r17 [1] SEQUENCE {
         scs-15kHz-r17 [0] ENUMERATED { n1(0), n2(1), n4(2), n6(3), n8(4), 
            n12(5), n16(6), n24(7), n32(8), n48(9), n64(10) } OPTIONAL,
         scs-30kHz-r17 [1] ENUMERATED { n1(0), n2(1), n4(2), n6(3), n8(4), 
            n12(5), n16(6), n24(7), n32(8), n48(9), n64(10) } OPTIONAL,
         scs-60kHz-r17 [2] ENUMERATED { n1(0), n2(1), n4(2), n6(3), n8(4), 
            n12(5), n16(6), n24(7), n32(8), n48(9), n64(10) } OPTIONAL,
         scs-120kHz-r17 [3] ENUMERATED { n1(0), n2(1), n4(2), n6(3), n8(4), 
            n12(5), n16(6), n24(7), n32(8), n48(9), n64(10) } OPTIONAL
      }
   } OPTIONAL,
     -- R1 33-5-1: SPS group-common PDSCH for multicast on PCell
   sps-Multicast-r17 [2] ENUMERATED { supported(0) } OPTIONAL
}

FeatureSetDownlink-v1730 ::= SEQUENCE {
     -- R1 25-19b: Support of PRS as spatial relation RS for SRS
   prs-AsSpatialRelationRS-For-SRS-r17 [0] ENUMERATED { supported(0) } OPTIONAL
}

-- TAG-SUPPORTEDAGGBANDWIDTH-STOP
-- TAG-SUPPORTEDBANDWIDTH-START
SupportedBandwidth ::= CHOICE {
   fr1 [0] ENUMERATED { mhz5(0), mhz10(1), mhz15(2), mhz20(3), mhz25(4), 
      mhz30(5), mhz40(6), mhz50(7), mhz60(8), mhz80(9), mhz100(10) },
   fr2 [1] ENUMERATED { mhz50(0), mhz100(1), mhz200(2), mhz400(3) }
}

-- TAG-FEATURESETDOWNLINKID-STOP
-- TAG-FEATURESETDOWNLINKPERCC-START
FeatureSetDownlinkPerCC ::= SEQUENCE {
   supportedSubcarrierSpacingDL [0] SubcarrierSpacing,
   supportedBandwidthDL [1] EXPLICIT SupportedBandwidth,
   channelBW-90mhz [2] ENUMERATED { supported(0) } OPTIONAL,
   maxNumberMIMO-LayersPDSCH [3] MIMO-LayersDL OPTIONAL,
   supportedModulationOrderDL [4] ModulationOrder OPTIONAL
}

MultiDCI-MultiTRP-r16 ::= SEQUENCE {
   maxNumberCORESET-r16 [0] ENUMERATED { n2(0), n3(1), n4(2), n5(3) },
   maxNumberCORESETPerPoolIndex-r16 [1] INTEGER (1..3),
   maxNumberUnicastPDSCH-PerPool-r16 [2] ENUMERATED { n1(0), n2(1), n3(2), 
      n4(3), n7(4) }
}

FeatureSetDownlinkPerCC-v1620 ::= SEQUENCE {
     -- R1 16-2a: Mulit-DCI based multi-TRP
   multiDCI-MultiTRP-r16 [0] MultiDCI-MultiTRP-r16 OPTIONAL,
     -- R1 16-2b-3: Support of single-DCI based FDMSchemeB
   supportFDM-SchemeB-r16 [1] ENUMERATED { supported(0) } OPTIONAL
}

SupportedBandwidth-v1700 ::= CHOICE {
   fr1-r17 [0] ENUMERATED { mhz5(0), mhz10(1), mhz15(2), mhz20(3), mhz25(4), 
      mhz30(5), mhz35(6), mhz40(7), mhz45(8), mhz50(9), mhz60(10), mhz70(11), 
      mhz80(12), mhz90(13), mhz100(14) },
   fr2-r17 [1] ENUMERATED { mhz50(0), mhz100(1), mhz200(2), mhz400(3), 
      mhz800(4), mhz1600(5), mhz2000(6) }
}

CRS-InterfMitigation-r17 ::= SEQUENCE {
     -- R4 24-1 CRS-IM (Interference Mitigation) in DSS scenario
   crs-IM-DSS-15kHzSCS-r17 [0] ENUMERATED { supported(0) } OPTIONAL,
     -- R4 24-2 CRS-IM in non-DSS and 15 kHz NR SCS scenario, without the assistance of network signaling on LTE channel bandwidth
   crs-IM-nonDSS-15kHzSCS-r17 [1] ENUMERATED { supported(0) } OPTIONAL,
     -- R4 24-3 CRS-IM in non-DSS and 15 kHz NR SCS scenario, with the assistance of network signaling on LTE channel bandwidth
   crs-IM-nonDSS-NWA-15kHzSCS-r17 [2] ENUMERATED { supported(0) } OPTIONAL,
     -- R4 24-4 CRS-IM in non-DSS and 30 kHz NR SCS scenario, without the assistance of network signaling on LTE channel bandwidth
   crs-IM-nonDSS-30kHzSCS-r17 [3] ENUMERATED { supported(0) } OPTIONAL,
     -- R4 24-5 CRS-IM in non-DSS and 30 kHz NR SCS scenario, with the assistance of network signaling on LTE channel bandwidth
   crs-IM-nonDSS-NWA-30kHzSCS-r17 [4] ENUMERATED { supported(0) } OPTIONAL
}

FeatureSetDownlinkPerCC-v1700 ::= SEQUENCE {
   supportedMinBandwidthDL-r17 [0] EXPLICIT SupportedBandwidth-v1700 OPTIONAL,
   broadcastSCell-r17 [1] ENUMERATED { supported(0) } OPTIONAL,
     -- R1 33-2g: MIMO layers for multicast PDSCH
   maxNumberMIMO-LayersMulticastPDSCH-r17 [2] ENUMERATED { n2(0), n4(1), n8(2)
       } OPTIONAL,
     -- R1 33-2h: Dynamic scheduling for multicast for SCell
   dynamicMulticastSCell-r17 [3] ENUMERATED { supported(0) } OPTIONAL,
   supportedBandwidthDL-v1710 [4] EXPLICIT SupportedBandwidth-v1700 OPTIONAL,
     -- R4 24-1/24-2/24-3/24-4/24-5
   supportedCRS-InterfMitigation-r17 [5] CRS-InterfMitigation-r17 OPTIONAL
}

FeatureSetDownlinkPerCC-v1720 ::= SEQUENCE {
     -- R1 33-2j: Supported maximum modulation order used for maximum data rate calculation for multicast PDSCH
   maxModulationOrderForMulticastDataRateCalculation-r17 [0] ENUMERATED { 
      qam64(0), qam256(1), qam1024(2) } OPTIONAL,
     -- R1 33-1-2: FDM-ed unicast PDSCH and group-common PDSCH for broadcast
   fdm-BroadcastUnicast-r17 [1] ENUMERATED { supported(0) } OPTIONAL,
     -- R1 33-3-2: FDM-ed unicast PDSCH and one group-common PDSCH for multicast
   fdm-MulticastUnicast-r17 [2] ENUMERATED { supported(0) } OPTIONAL
}

FeatureSetDownlinkPerCC-v1730 ::= SEQUENCE {
     -- R1 33-3-3: Intra-slot TDM-ed unicast PDSCH and group-common PDSCH
   intraSlotTDM-UnicastGroupCommonPDSCH-r17 [0] ENUMERATED { yes(0), no(1) }
       OPTIONAL,
     -- R1 33-5-3: One SPS group-common PDSCH configuration for multicast for SCell
   sps-MulticastSCell-r17 [1] ENUMERATED { supported(0) } OPTIONAL,
     -- R1 33-5-4: Up to 8 SPS group-common PDSCH configurations per CFR for multicast for SCell
   sps-MulticastSCellMultiConfig-r17 [2] INTEGER (1..8) OPTIONAL,
     -- R1 33-1-1: Dynamic slot-level repetition for broadcast MTCH
   dci-BroadcastWith16Repetitions-r17 [3] ENUMERATED { supported(0) } OPTIONAL
}

FeatureSetDownlinkPerCC-v1780 ::= SEQUENCE {
   supportedBandwidthDL-v1780 [0] EXPLICIT SupportedBandwidth-v1700 OPTIONAL
}

DummyI ::= SEQUENCE {
   supportedSRS-TxPortSwitch [0] ENUMERATED { t1r2(0), t1r4(1), t2r4(2), 
      t1r4-t2r4(3), tr-equal(4) },
   txSwitchImpactToRx [1] ENUMERATED { true(0) } OPTIONAL
}

DummyF ::= SEQUENCE {
   maxNumberPeriodicCSI-ReportPerBWP [0] INTEGER (1..4),
   maxNumberAperiodicCSI-ReportPerBWP [1] INTEGER (1..4),
   maxNumberSemiPersistentCSI-ReportPerBWP [2] INTEGER (0..4),
   simultaneousCSI-ReportsAllCC [3] INTEGER (5..32)
}

-- TAG-FEATURESETS-STOP
-- TAG-FEATURESETUPLINK-START
FeatureSetUplink ::= SEQUENCE {
   featureSetListPerUplinkCC [0] SEQUENCE (SIZE (1..maxNrofServingCells)) OF 
      FeatureSetUplinkPerCC-Id,
   scalingFactor [1] ENUMERATED { f0p4(0), f0p75(1), f0p8(2) } OPTIONAL,
   dummy3 [2] ENUMERATED { supported(0) } OPTIONAL,
   intraBandFreqSeparationUL [3] FreqSeparationClass OPTIONAL,
   searchSpaceSharingCA-UL [4] ENUMERATED { supported(0) } OPTIONAL,
   dummy1 [5] DummyI OPTIONAL,
   supportedSRS-Resources [6] SRS-Resources OPTIONAL,
   twoPUCCH-Group [7] ENUMERATED { supported(0) } OPTIONAL,
   dynamicSwitchSUL [8] ENUMERATED { supported(0) } OPTIONAL,
   simultaneousTxSUL-NonSUL [9] ENUMERATED { supported(0) } OPTIONAL,
   pusch-ProcessingType1-DifferentTB-PerSlot [10] SEQUENCE {
      scs-15kHz [0] ENUMERATED { upto2(0), upto4(1), upto7(2) } OPTIONAL,
      scs-30kHz [1] ENUMERATED { upto2(0), upto4(1), upto7(2) } OPTIONAL,
      scs-60kHz [2] ENUMERATED { upto2(0), upto4(1), upto7(2) } OPTIONAL,
      scs-120kHz [3] ENUMERATED { upto2(0), upto4(1), upto7(2) } OPTIONAL
   } OPTIONAL,
   dummy2 [11] DummyF OPTIONAL
}

-- TAG-FEATURESETUPLINKID-STOP
-- TAG-FEATURESETUPLINKPERCC-START
FeatureSetUplinkPerCC ::= SEQUENCE {
   supportedSubcarrierSpacingUL [0] SubcarrierSpacing,
   supportedBandwidthUL [1] EXPLICIT SupportedBandwidth,
   channelBW-90mhz [2] ENUMERATED { supported(0) } OPTIONAL,
   mimo-CB-PUSCH [3] SEQUENCE {
      maxNumberMIMO-LayersCB-PUSCH [0] MIMO-LayersUL OPTIONAL,
      maxNumberSRS-ResourcePerSet [1] INTEGER (1..2)
   } OPTIONAL,
   maxNumberMIMO-LayersNonCB-PUSCH [4] MIMO-LayersUL OPTIONAL,
   supportedModulationOrderUL [5] ModulationOrder OPTIONAL
}

FeatureSetUplink-v1540 ::= SEQUENCE {
   zeroSlotOffsetAperiodicSRS [0] ENUMERATED { supported(0) } OPTIONAL,
   pa-PhaseDiscontinuityImpacts [1] ENUMERATED { supported(0) } OPTIONAL,
   pusch-SeparationWithGap [2] ENUMERATED { supported(0) } OPTIONAL,
   pusch-ProcessingType2 [3] SEQUENCE {
      scs-15kHz [0] ProcessingParameters OPTIONAL,
      scs-30kHz [1] ProcessingParameters OPTIONAL,
      scs-60kHz [2] ProcessingParameters OPTIONAL
   } OPTIONAL,
   ul-MCS-TableAlt-DynamicIndication [4] ENUMERATED { supported(0) } OPTIONAL
}

FeatureSetUplinkPerCC-v1540 ::= SEQUENCE {
   mimo-NonCB-PUSCH [0] SEQUENCE {
      maxNumberSRS-ResourcePerSet [0] INTEGER (1..4),
      maxNumberSimultaneousSRS-ResourceTx [1] INTEGER (1..4)
   } OPTIONAL
}

SRS-PosResources-r16 ::= SEQUENCE {
   maxNumberSRS-PosResourceSetPerBWP-r16 [0] ENUMERATED { n1(0), n2(1), n4(2), 
      n8(3), n12(4), n16(5) },
   maxNumberSRS-PosResourcesPerBWP-r16 [1] ENUMERATED { n1(0), n2(1), n4(2), 
      n8(3), n16(4), n32(5), n64(6) },
   maxNumberSRS-ResourcesPerBWP-PerSlot-r16 [2] ENUMERATED { n1(0), n2(1), 
      n3(2), n4(3), n5(4), n6(5), n8(6), n10(7), n12(8), n14(9) },
   maxNumberPeriodicSRS-PosResourcesPerBWP-r16 [3] ENUMERATED { n1(0), n2(1), 
      n4(2), n8(3), n16(4), n32(5), n64(6) },
   maxNumberPeriodicSRS-PosResourcesPerBWP-PerSlot-r16 [4] ENUMERATED { n1(0), 
      n2(1), n3(2), n4(3), n5(4), n6(5), n8(6), n10(7), n12(8), n14(9) }
}

SRS-PosResourceAP-r16 ::= SEQUENCE {
   maxNumberAP-SRS-PosResourcesPerBWP-r16 [0] ENUMERATED { n1(0), n2(1), n4(2)
      , n8(3), n16(4), n32(5), n64(6) },
   maxNumberAP-SRS-PosResourcesPerBWP-PerSlot-r16 [1] ENUMERATED { n1(0), n2(1)
      , n3(2), n4(3), n5(4), n6(5), n8(6), n10(7), n12(8), n14(9) }
}

SRS-PosResourceSP-r16 ::= SEQUENCE {
   maxNumberSP-SRS-PosResourcesPerBWP-r16 [0] ENUMERATED { n1(0), n2(1), n4(2)
      , n8(3), n16(4), n32(5), n64(6) },
   maxNumberSP-SRS-PosResourcesPerBWP-PerSlot-r16 [1] ENUMERATED { n1(0), n2(1)
      , n3(2), n4(3), n5(4), n6(5), n8(6), n10(7), n12(8), n14(9) }
}

SRS-AllPosResources-r16 ::= SEQUENCE {
   srs-PosResources-r16 [0] SRS-PosResources-r16,
   srs-PosResourceAP-r16 [1] SRS-PosResourceAP-r16 OPTIONAL,
   srs-PosResourceSP-r16 [2] SRS-PosResourceSP-r16 OPTIONAL
}

FeatureSetUplink-v1610 ::= SEQUENCE {
     -- R1 11-5: PUsCH repetition Type B
   pusch-RepetitionTypeB-r16 [0] SEQUENCE {
      maxNumberPUSCH-Tx-r16 [0] ENUMERATED { n2(0), n3(1), n4(2), n7(3), n8(4)
         , n12(5) },
      hoppingScheme-r16 [1] ENUMERATED { interSlotHopping(0), 
         interRepetitionHopping(1), both(2) }
   } OPTIONAL,
     -- R1 11-7: UL cancelation scheme for self-carrier
   ul-CancellationSelfCarrier-r16 [1] ENUMERATED { supported(0) } OPTIONAL,
     -- R1 11-7a: UL cancelation scheme for cross-carrier
   ul-CancellationCrossCarrier-r16 [2] ENUMERATED { supported(0) } OPTIONAL,
     -- R1 16-5c: The maximum number of SRS resources in one SRS resource set with usage set to 'codebook' for Mode 2
   ul-FullPwrMode2-MaxSRS-ResInSet-r16 [3] ENUMERATED { n1(0), n2(1), n4(2) }
       OPTIONAL,
     -- R1 22-4a/4b/4c/4d: CBG based transmission for UL with unicast PUSCH(s) per slot per CC with UE processing time Capability 1
   cbgPUSCH-ProcessingType1-DifferentTB-PerSlot-r16 [4] SEQUENCE {
      scs-15kHz-r16 [0] ENUMERATED { one-pusch(0), upto2(1), upto4(2), upto7(3)
          } OPTIONAL,
      scs-30kHz-r16 [1] ENUMERATED { one-pusch(0), upto2(1), upto4(2), upto7(3)
          } OPTIONAL,
      scs-60kHz-r16 [2] ENUMERATED { one-pusch(0), upto2(1), upto4(2), upto7(3)
          } OPTIONAL,
      scs-120kHz-r16 [3] ENUMERATED { one-pusch(0), upto2(1), upto4(2), 
         upto7(3) } OPTIONAL
   } OPTIONAL,
     -- R1 22-3a/3b/3c/3d: CBG based transmission for UL with unicast PUSCH(s) per slot per CC with UE processing time Capability 2
   cbgPUSCH-ProcessingType2-DifferentTB-PerSlot-r16 [5] SEQUENCE {
      scs-15kHz-r16 [0] ENUMERATED { one-pusch(0), upto2(1), upto4(2), upto7(3)
          } OPTIONAL,
      scs-30kHz-r16 [1] ENUMERATED { one-pusch(0), upto2(1), upto4(2), upto7(3)
          } OPTIONAL,
      scs-60kHz-r16 [2] ENUMERATED { one-pusch(0), upto2(1), upto4(2), upto7(3)
          } OPTIONAL,
      scs-120kHz-r16 [3] ENUMERATED { one-pusch(0), upto2(1), upto4(2), 
         upto7(3) } OPTIONAL
   } OPTIONAL,
   supportedSRS-PosResources-r16 [6] SRS-AllPosResources-r16 OPTIONAL,
   intraFreqDAPS-UL-r16 [7] SEQUENCE {
      dummy [0] ENUMERATED { supported(0) } OPTIONAL,
      intraFreqTwoTAGs-DAPS-r16 [1] ENUMERATED { supported(0) } OPTIONAL,
      dummy1 [2] ENUMERATED { supported(0) } OPTIONAL,
      dummy2 [3] ENUMERATED { supported(0) } OPTIONAL,
      dummy3 [4] ENUMERATED { short(0), long(1) } OPTIONAL
   } OPTIONAL,
   intraBandFreqSeparationUL-v1620 [8] FreqSeparationClassUL-v1620 OPTIONAL,
     -- R1 11-3: More than one PUCCH for HARQ-ACK transmission within a slot
   multiPUCCH-r16 [9] SEQUENCE {
      sub-SlotConfig-NCP-r16 [0] ENUMERATED { set1(0), set2(1) } OPTIONAL,
      sub-SlotConfig-ECP-r16 [1] ENUMERATED { set1(0), set2(1) } OPTIONAL
   } OPTIONAL,
     -- R1 11-3c: 2 PUCCH of format 0 or 2 for a single 7*2-symbol subslot based HARQ-ACK codebook
   twoPUCCH-Type1-r16 [10] ENUMERATED { supported(0) } OPTIONAL,
     -- R1 11-3d: 2 PUCCH of format 0 or 2 for a single 2*7-symbol subslot based HARQ-ACK codebook
   twoPUCCH-Type2-r16 [11] ENUMERATED { supported(0) } OPTIONAL,
     -- R1 11-3e: 1 PUCCH format 0 or 2 and 1 PUCCH format 1, 3 or 4 in the same subslot for a single 2*7-symbol HARQ-ACK codebooks
   twoPUCCH-Type3-r16 [12] ENUMERATED { supported(0) } OPTIONAL,
     -- R1 11-3f: 2 PUCCH transmissions in the same subslot for a single 2*7-symbol HARQ-ACK codebooks which are not covered by 11-3d and
     -- 11-3e
   twoPUCCH-Type4-r16 [13] ENUMERATED { supported(0) } OPTIONAL,
     -- R1 11-3g: SR/HARQ-ACK multiplexing once per subslot using a PUCCH (or HARQ-ACK piggybacked on a PUSCH) when SR/HARQ-ACK
     -- are supposed to be sent with different starting symbols in a subslot
   mux-SR-HARQ-ACK-r16 [14] ENUMERATED { supported(0) } OPTIONAL,
   dummy1 [15] ENUMERATED { supported(0) } OPTIONAL,
   dummy2 [16] ENUMERATED { supported(0) } OPTIONAL,
     -- R1 11-4c: 2 PUCCH of format 0 or 2 for two HARQ-ACK codebooks with one 7*2-symbol sub-slot based HARQ-ACK codebook
   twoPUCCH-Type5-r16 [17] ENUMERATED { supported(0) } OPTIONAL,
     -- R1 11-4d: 2 PUCCH of format 0 or 2 in consecutive symbols for two HARQ-ACK codebooks with one 2*7-symbol sub-slot based HARQ-ACK
     -- codebook
   twoPUCCH-Type6-r16 [18] ENUMERATED { supported(0) } OPTIONAL,
     -- R1 11-4e: 2 PUCCH of format 0 or 2 for two subslot based HARQ-ACK codebooks
   twoPUCCH-Type7-r16 [19] ENUMERATED { supported(0) } OPTIONAL,
     -- R1 11-4f: 1 PUCCH format 0 or 2 and 1 PUCCH format 1, 3 or 4 in the same subslot for HARQ-ACK codebooks with one 2*7-symbol
     -- subslot based HARQ-ACK codebook
   twoPUCCH-Type8-r16 [20] ENUMERATED { supported(0) } OPTIONAL,
     -- R1 11-4g: 1 PUCCH format 0 or 2 and 1 PUCCH format 1, 3 or 4 in the same subslot for two subslot based HARQ-ACK codebooks
   twoPUCCH-Type9-r16 [21] ENUMERATED { supported(0) } OPTIONAL,
     -- R1 11-4h: 2 PUCCH transmissions in the same subslot for two HARQ-ACK codebooks with one 2*7-symbol subslot which are not covered
     -- by 11-4c and 11-4e
   twoPUCCH-Type10-r16 [22] ENUMERATED { supported(0) } OPTIONAL,
     -- R1 11-4i: 2 PUCCH transmissions in the same subslot for two subslot based HARQ-ACK codebooks which are not covered by 11-4d and
     -- 11-4f
   twoPUCCH-Type11-r16 [23] ENUMERATED { supported(0) } OPTIONAL,
     -- R1 12-1: UL intra-UE multiplexing/prioritization of overlapping channel/signals with two priority levels in physical layer
   ul-IntraUE-Mux-r16 [24] SEQUENCE {
      pusch-PreparationLowPriority-r16 [0] ENUMERATED { sym0(0), sym1(1), 
         sym2(2) },
      pusch-PreparationHighPriority-r16 [1] ENUMERATED { sym0(0), sym1(1), 
         sym2(2) }
   } OPTIONAL,
     -- R1 16-5a: Supported UL full power transmission mode of fullpower
   ul-FullPwrMode-r16 [25] ENUMERATED { supported(0) } OPTIONAL,
     -- R1 18-5d: Processing up to X unicast DCI scheduling for UL per scheduled CC
   crossCarrierSchedulingProcessing-DiffSCS-r16 [26] SEQUENCE {
      scs-15kHz-120kHz-r16 [0] ENUMERATED { n1(0), n2(1), n4(2) } OPTIONAL,
      scs-15kHz-60kHz-r16 [1] ENUMERATED { n1(0), n2(1), n4(2) } OPTIONAL,
      scs-30kHz-120kHz-r16 [2] ENUMERATED { n1(0), n2(1), n4(2) } OPTIONAL,
      scs-15kHz-30kHz-r16 [3] ENUMERATED { n2(0) } OPTIONAL,
      scs-30kHz-60kHz-r16 [4] ENUMERATED { n2(0) } OPTIONAL,
      scs-60kHz-120kHz-r16 [5] ENUMERATED { n2(0) } OPTIONAL
   } OPTIONAL,
     -- R1 16-5b: Supported UL full power transmission mode of fullpowerMode1
   ul-FullPwrMode1-r16 [27] ENUMERATED { supported(0) } OPTIONAL,
     -- R1 16-5c-2: Ports configuration for Mode 2
   ul-FullPwrMode2-SRSConfig-diffNumSRSPorts-r16 [28] ENUMERATED { p1-2(0), 
      p1-4(1), p1-2-4(2) } OPTIONAL,
     -- R1 16-5c-3: TPMI group for Mode 2
   ul-FullPwrMode2-TPMIGroup-r16 [29] SEQUENCE {
      twoPorts-r16 [0] BIT STRING  (SIZE (2)) OPTIONAL,
      fourPortsNonCoherent-r16 [1] ENUMERATED { g0(0), g1(1), g2(2), g3(3) }
          OPTIONAL,
      fourPortsPartialCoherent-r16 [2] ENUMERATED { g0(0), g1(1), g2(2), g3(3)
         , g4(4), g5(5), g6(6) } OPTIONAL
   } OPTIONAL
}

FeatureSetUplink-v1630 ::= SEQUENCE {
     -- R1 22-8: For SRS for CB PUSCH and antenna switching on FR1 with symbol level offset for aperiodic SRS transmission
   offsetSRS-CB-PUSCH-Ant-Switch-fr1-r16 [0] ENUMERATED { supported(0) }
       OPTIONAL,
     -- R1 22-8a: PDCCH monitoring on any span of up to 3 consecutive OFDM symbols of a slot and constrained timeline for SRS for CB
     -- PUSCH and antenna switching on FR1
   offsetSRS-CB-PUSCH-PDCCH-MonitorSingleOcc-fr1-r16 [1] ENUMERATED { 
      supported(0) } OPTIONAL,
     -- R1 22-8b: For type 1 CSS with dedicated RRC configuration, type 3 CSS, and UE-SS, monitoring occasion can be any OFDM symbol(s)
     -- of a slot for Case 2 and constrained timeline for SRS for CB PUSCH and antenna switching on FR1
   offsetSRS-CB-PUSCH-PDCCH-MonitorAnyOccWithoutGap-fr1-r16 [2] ENUMERATED { 
      supported(0) } OPTIONAL,
     -- R1 22-8c: For type 1 CSS with dedicated RRC configuration, type 3 CSS, and UE-SS, monitoring occasion can be any OFDM symbol(s)
     -- of a slot for Case 2 with a DCI gap and constrained timeline for SRS for CB PUSCH and antenna switching on FR1
   offsetSRS-CB-PUSCH-PDCCH-MonitorAnyOccWithGap-fr1-r16 [3] ENUMERATED { 
      supported(0) } OPTIONAL,
   dummy [4] ENUMERATED { supported(0) } OPTIONAL,
     -- R1 22-9: Cancellation of PUCCH, PUSCH or PRACH with a DCI scheduling a PDSCH or CSI-RS or a DCI format 2_0 for SFI
   partialCancellationPUCCH-PUSCH-PRACH-TX-r16 [5] ENUMERATED { supported(0) }
       OPTIONAL
}

SubSlot-Config-r16 ::= SEQUENCE {
   sub-SlotConfig-NCP-r16 [0] ENUMERATED { n4(0), n5(1), n6(2), n7(3) }
       OPTIONAL,
   sub-SlotConfig-ECP-r16 [1] ENUMERATED { n4(0), n5(1), n6(2) } OPTIONAL
}

FeatureSetUplink-v1640 ::= SEQUENCE {
    -- R1 11-4: Two HARQ-ACK codebooks with up to one sub-slot based HARQ-ACK codebook (i.e. slot-based + slot-based, or slot-based +
     -- sub-slot based) simultaneously constructed for supporting HARQ-ACK codebooks with different priorities at a UE
   twoHARQ-ACK-Codebook-type1-r16 [0] SubSlot-Config-r16 OPTIONAL,
     -- R1 11-4a: Two sub-slot based HARQ-ACK codebooks simultaneously constructed for supporting HARQ-ACK codebooks with different
     -- priorities at a UE
   twoHARQ-ACK-Codebook-type2-r16 [1] SubSlot-Config-r16 OPTIONAL,
     -- R1 22-8d: All PDCCH monitoring occasion can be any OFDM symbol(s) of a slot for Case 2 with a span gap and constrained timeline
     -- for SRS for CB PUSCH and antenna switching on FR1
   offsetSRS-CB-PUSCH-PDCCH-MonitorAnyOccWithSpanGap-fr1-r16 [2] SEQUENCE {
      scs-15kHz-r16 [0] ENUMERATED { set1(0), set2(1), set3(2) } OPTIONAL,
      scs-30kHz-r16 [1] ENUMERATED { set1(0), set2(1), set3(2) } OPTIONAL,
      scs-60kHz-r16 [2] ENUMERATED { set1(0), set2(1), set3(2) } OPTIONAL
   } OPTIONAL
}

FeatureSetUplink-v1710 ::= SEQUENCE {
     -- R1 23-3-1	Multi-TRP PUSCH repetition (type A) -codebook based
   mTRP-PUSCH-TypeA-CB-r17 [0] ENUMERATED { n1(0), n2(1), n4(2) } OPTIONAL,
     -- R1 23-3-1-2	Multi-TRP PUSCH repetition (type A) - non-codebook based
   mTRP-PUSCH-RepetitionTypeA-r17 [1] ENUMERATED { n1(0), n2(1), n3(2), n4(3) }
       OPTIONAL,
     -- R1 23-3-3	Multi-TRP PUCCH repetition-intra-slot
   mTRP-PUCCH-IntraSlot-r17 [2] ENUMERATED { pf0-2(0), pf1-3-4(1), pf0-4(2) }
       OPTIONAL,
     -- R1 23-8-4	Maximum 2 SP and 1 periodic SRS sets for antenna switching
   srs-AntennaSwitching2SP-1Periodic-r17 [3] ENUMERATED { supported(0) }
       OPTIONAL,
     -- R1 23-8-9	Extension of aperiodic SRS configuration for 1T4R, 1T2R and 2T4R
   srs-ExtensionAperiodicSRS-r17 [4] ENUMERATED { supported(0) } OPTIONAL,
     -- R1 23-8-10	1 aperiodic SRS resource set for 1T4R
   srs-OneAP-SRS-r17 [5] ENUMERATED { supported(0) } OPTIONAL,
     -- R4 16-8 UE power class per band per band combination
   ue-PowerClassPerBandPerBC-r17 [6] ENUMERATED { pc1dot5(0), pc2(1), pc3(2) }
       OPTIONAL,
     -- R4 17-8 UL transmission in FR2 bands within an UL gap when the UL gap is activated
   tx-Support-UL-GapFR2-r17 [7] ENUMERATED { supported(0) } OPTIONAL
}

FeatureSetUplinkPerCC-v1700 ::= SEQUENCE {
   supportedMinBandwidthUL-r17 [0] EXPLICIT SupportedBandwidth-v1700 OPTIONAL,
     -- R1 23-3-1-3	FeMIMO: Multi-TRP PUSCH repetition (type B) - non-codebook based
   mTRP-PUSCH-RepetitionTypeB-r17 [1] ENUMERATED { n1(0), n2(1), n3(2), n4(3) }
       OPTIONAL,
     -- R1 23-3-1-1 -codebook based Multi-TRP PUSCH repetition (type B)
   mTRP-PUSCH-TypeB-CB-r17 [2] ENUMERATED { n1(0), n2(1), n4(2) } OPTIONAL,
   supportedBandwidthUL-v1710 [3] EXPLICIT SupportedBandwidth-v1700 OPTIONAL
}

FeatureSetUplink-v1720 ::= SEQUENCE {
     -- R1 25-3: Repetitions for PUCCH format 0, 1, 2, 3 and 4 over multiple PUCCH subslots with configured K = 2, 4, 8
   pucch-Repetition-F0-1-2-3-4-RRC-Config-r17 [0] ENUMERATED { supported(0) }
       OPTIONAL,
     -- R1 25-3a: Repetitions for PUCCH format 0, 1, 2, 3 and 4 over multiple PUCCH subslots using dynamic repetition indication
   pucch-Repetition-F0-1-2-3-4-DynamicIndication-r17 [1] ENUMERATED { 
      supported(0) } OPTIONAL,
     -- R1 25-3b: Inter-subslot frequency hopping for PUCCH repetitions
   interSubslotFreqHopping-PUCCH-r17 [2] ENUMERATED { supported(0) } OPTIONAL,
     -- R1 25-8: Semi-static HARQ-ACK codebook for sub-slot PUCCH
   semiStaticHARQ-ACK-CodebookSub-SlotPUCCH-r17 [3] ENUMERATED { supported(0) }
       OPTIONAL,
     -- R1 25-14: PHY prioritization of overlapping low-priority DG-PUSCH and high-priority CG-PUSCH
   phy-PrioritizationLowPriorityDG-HighPriorityCG-r17 [4] INTEGER (1..16) OPTIONAL
      ,
     -- R1 25-15: PHY prioritization of overlapping high-priority DG-PUSCH and low-priority CG-PUSCH
   phy-PrioritizationHighPriorityDG-LowPriorityCG-r17 [5] SEQUENCE {
      pusch-PreparationLowPriority-r17 [0] ENUMERATED { sym0(0), sym1(1), 
         sym2(2) },
      additionalCancellationTime-r17 [1] SEQUENCE {
         scs-15kHz-r17 [0] ENUMERATED { sym0(0), sym1(1), sym2(2) } OPTIONAL,
         scs-30kHz-r17 [1] ENUMERATED { sym0(0), sym1(1), sym2(2), sym3(3), 
            sym4(4) } OPTIONAL,
         scs-60kHz-r17 [2] ENUMERATED { sym0(0), sym1(1), sym2(2), sym3(3), 
            sym4(4), sym5(5), sym6(6), sym7(7), sym8(8) } OPTIONAL,
         scs-120kHz-r17 [3] ENUMERATED { sym0(0), sym1(1), sym2(2), sym3(3), 
            sym4(4), sym5(5), sym6(6), sym7(7), sym8(8), sym9(9), sym10(10), 
            sym11(11), sym12(12), sym13(13), sym14(14), sym15(15), sym16(16) }
             OPTIONAL
      },
      maxNumberCarriers-r17 [2] INTEGER (1..16)
   } OPTIONAL,
     -- R4 17-5 Support of UL DC location(s) report
   extendedDC-LocationReport-r17 [6] ENUMERATED { supported(0) } OPTIONAL
}

FeatureSetUplinkPerCC-v1780 ::= SEQUENCE {
   supportedBandwidthUL-v1780 [0] EXPLICIT SupportedBandwidth-v1700 OPTIONAL
}

-- TAG-FEATURESETEUTRAUPLINKID-STOP
-- TAG-FEATURESETS-START
FeatureSets ::= SEQUENCE {
   featureSetsDownlink [0] SEQUENCE (SIZE (1..maxDownlinkFeatureSets)) OF FeatureSetDownlink OPTIONAL,
   featureSetsDownlinkPerCC [1] SEQUENCE (SIZE (1..maxPerCC-FeatureSets)) OF FeatureSetDownlinkPerCC
       OPTIONAL,
   featureSetsUplink [2] SEQUENCE (SIZE (1..maxUplinkFeatureSets)) OF FeatureSetUplink OPTIONAL,
   featureSetsUplinkPerCC [3] SEQUENCE (SIZE (1..maxPerCC-FeatureSets)) OF FeatureSetUplinkPerCC
       OPTIONAL,
   ...,
   [[
      featureSetsDownlink-v1540 [4] SEQUENCE (SIZE (1..maxDownlinkFeatureSets)) OF 
         FeatureSetDownlink-v1540 OPTIONAL,
      featureSetsUplink-v1540 [5] SEQUENCE (SIZE (1..maxUplinkFeatureSets)) OF 
         FeatureSetUplink-v1540 OPTIONAL,
      featureSetsUplinkPerCC-v1540 [6] SEQUENCE (SIZE (1..maxPerCC-FeatureSets)) OF 
         FeatureSetUplinkPerCC-v1540 OPTIONAL
   ]],
   [[
      featureSetsDownlink-v15a0 [7] SEQUENCE (SIZE (1..maxDownlinkFeatureSets)) OF 
         FeatureSetDownlink-v15a0 OPTIONAL
   ]],
   [[
      featureSetsDownlink-v1610 [8] SEQUENCE (SIZE (1..maxDownlinkFeatureSets)) OF 
         FeatureSetDownlink-v1610 OPTIONAL,
      featureSetsUplink-v1610 [9] SEQUENCE (SIZE (1..maxUplinkFeatureSets)) OF 
         FeatureSetUplink-v1610 OPTIONAL,
      featureSetDownlinkPerCC-v1620 [10] SEQUENCE (SIZE (1..maxPerCC-FeatureSets)) OF 
         FeatureSetDownlinkPerCC-v1620 OPTIONAL
   ]],
   [[
      featureSetsUplink-v1630 [11] SEQUENCE (SIZE (1..maxUplinkFeatureSets)) OF 
         FeatureSetUplink-v1630 OPTIONAL
   ]],
   [[
      featureSetsUplink-v1640 [12] SEQUENCE (SIZE (1..maxUplinkFeatureSets)) OF 
         FeatureSetUplink-v1640 OPTIONAL
   ]],
   [[
      featureSetsDownlink-v1700 [13] SEQUENCE (SIZE (1..maxDownlinkFeatureSets)) OF 
         FeatureSetDownlink-v1700 OPTIONAL,
      featureSetsDownlinkPerCC-v1700 [14] SEQUENCE (SIZE (1..maxPerCC-FeatureSets)) OF 
         FeatureSetDownlinkPerCC-v1700 OPTIONAL,
      featureSetsUplink-v1710 [15] SEQUENCE (SIZE (1..maxUplinkFeatureSets)) OF 
         FeatureSetUplink-v1710 OPTIONAL,
      featureSetsUplinkPerCC-v1700 [16] SEQUENCE (SIZE (1..maxPerCC-FeatureSets)) OF 
         FeatureSetUplinkPerCC-v1700 OPTIONAL
   ]],
   [[
      featureSetsDownlink-v1720 [17] SEQUENCE (SIZE (1..maxDownlinkFeatureSets)) OF 
         FeatureSetDownlink-v1720 OPTIONAL,
      featureSetsDownlinkPerCC-v1720 [18] SEQUENCE (SIZE (1..maxPerCC-FeatureSets)) OF 
         FeatureSetDownlinkPerCC-v1720 OPTIONAL,
      featureSetsUplink-v1720 [19] SEQUENCE (SIZE (1..maxUplinkFeatureSets)) OF 
         FeatureSetUplink-v1720 OPTIONAL
   ]],
   [[
      featureSetsDownlink-v1730 [20] SEQUENCE (SIZE (1..maxDownlinkFeatureSets)) OF 
         FeatureSetDownlink-v1730 OPTIONAL,
      featureSetsDownlinkPerCC-v1730 [21] SEQUENCE (SIZE (1..maxPerCC-FeatureSets)) OF 
         FeatureSetDownlinkPerCC-v1730 OPTIONAL
   ]],
   [[
      featureSetsDownlinkPerCC-v1780 [22] SEQUENCE (SIZE (1..maxPerCC-FeatureSets)) OF 
         FeatureSetDownlinkPerCC-v1780 OPTIONAL,
      featureSetsUplinkPerCC-v1780 [23] SEQUENCE (SIZE (1..maxPerCC-FeatureSets)) OF 
         FeatureSetUplinkPerCC-v1780 OPTIONAL
   ]]
}

FeatureSetUplink-v16d0 ::= SEQUENCE {
   pusch-RepetitionTypeB-v16d0 [0] SEQUENCE {
      maxNumberPUSCH-Tx-Cap1-r16 [0] ENUMERATED { n2(0), n3(1), n4(2), n7(3), 
         n8(4), n12(5) },
      maxNumberPUSCH-Tx-Cap2-r16 [1] ENUMERATED { n2(0), n3(1), n4(2), n7(3), 
         n8(4), n12(5) }
   } OPTIONAL
}

FeatureSets-v16d0 ::= SEQUENCE {
   featureSetsUplink-v16d0 [0] SEQUENCE (SIZE (1..maxUplinkFeatureSets)) OF FeatureSetUplink-v16d0
       OPTIONAL
}

FreqBandInformationEUTRA ::= SEQUENCE {
   bandEUTRA [0] FreqBandIndicatorEUTRA,
   ca-BandwidthClassDL-EUTRA [1] CA-BandwidthClassEUTRA OPTIONAL, -- Need N
   ca-BandwidthClassUL-EUTRA [2] CA-BandwidthClassEUTRA OPTIONAL -- Need N
}

FreqBandInformationNR ::= SEQUENCE {
   bandNR [0] FreqBandIndicatorNR,
   maxBandwidthRequestedDL [1] AggregatedBandwidth OPTIONAL, -- Need N
   maxBandwidthRequestedUL [2] AggregatedBandwidth OPTIONAL, -- Need N
   maxCarriersRequestedDL [3] INTEGER (1..maxNrofServingCells) OPTIONAL, -- Need N
   maxCarriersRequestedUL [4] INTEGER (1..maxNrofServingCells) OPTIONAL -- Need N
}

FreqBandInformation ::= CHOICE {
   bandInformationEUTRA [0] FreqBandInformationEUTRA,
   bandInformationNR [1] FreqBandInformationNR
}

-- TAG-FREQBANDINDICATOREUTRA-STOP
-- TAG-FREQBANDLIST-START
FreqBandList ::= SEQUENCE (SIZE (1..maxBandsMRDC)) OF FreqBandInformation

-- TAG-FREQSEPARATIONCLASSDL-Only-STOP
-- TAG-FR2-2-ACCESSPARAMSPERBAND-START
FR2-2-AccessParamsPerBand-r17 ::= SEQUENCE {
     -- R1 24-1: Basic FR2-2 DL support
   dl-FR2-2-SCS-120kHz-r17 [0] ENUMERATED { supported(0) } OPTIONAL,
     -- R1 24-1a: Basic FR2-2 UL support
   ul-FR2-2-SCS-120kHz-r17 [1] ENUMERATED { supported(0) } OPTIONAL,
     -- R1 24-2: 120KHz SSB support for initial access in FR2-2
   initialAccessSSB-120kHz-r17 [2] ENUMERATED { supported(0) } OPTIONAL,
     -- R1 24-1b: Wideband PRACH for 120 kHz in FR2-2
   widebandPRACH-SCS-120kHz-r17 [3] ENUMERATED { supported(0) } OPTIONAL,
     -- R1 24-1c: Multi-RB support PUCCH format 0/1/4 for 120 kHz in FR2-2
   multiRB-PUCCH-SCS-120kHz-r17 [4] ENUMERATED { supported(0) } OPTIONAL,
     -- R1 24-1d: Multiple PDSCH scheduling by single DCI for 120kHz in FR2-2
   multiPDSCH-SingleDCI-FR2-2-SCS-120kHz-r17 [5] ENUMERATED { supported(0) }
       OPTIONAL,
     -- R1 24-1e: Multiple PUSCH scheduling by single DCI for 120kHz in FR2-2
   multiPUSCH-SingleDCI-FR2-2-SCS-120kHz-r17 [6] ENUMERATED { supported(0) }
       OPTIONAL,
     -- R1 24-4: 480KHz SCS support for DL
   dl-FR2-2-SCS-480kHz-r17 [7] ENUMERATED { supported(0) } OPTIONAL,
     -- R1 24-4a: 480KHz SCS support for UL
   ul-FR2-2-SCS-480kHz-r17 [8] ENUMERATED { supported(0) } OPTIONAL,
     -- R1 24-3: 480KHz SSB support for initial access in FR2-2
   initialAccessSSB-480kHz-r17 [9] ENUMERATED { supported(0) } OPTIONAL,
     -- R1 24-4b: Wideband PRACH for 480 kHz in FR2-2
   widebandPRACH-SCS-480kHz-r17 [10] ENUMERATED { supported(0) } OPTIONAL,
     -- R1 24-4c: Multi-RB support PUCCH format 0/1/4 for 480 kHz in FR2-2
   multiRB-PUCCH-SCS-480kHz-r17 [11] ENUMERATED { supported(0) } OPTIONAL,
     -- R1 24-4f: Enhanced PDCCH monitoring for 480KHz in FR2-2
   enhancedPDCCH-monitoringSCS-480kHz-r17 [12] ENUMERATED { supported(0) }
       OPTIONAL,
     -- R1 24-5: 960KHz SCS support for DL
   dl-FR2-2-SCS-960kHz-r17 [13] ENUMERATED { supported(0) } OPTIONAL,
     -- R1 24-5a: 960KHz SCS support for UL
   ul-FR2-2-SCS-960kHz-r17 [14] ENUMERATED { supported(0) } OPTIONAL,
     -- R1 24-5c: Multi-RB support PUCCH format 0/1/4 for 960 kHz in FR2-2
   multiRB-PUCCH-SCS-960kHz-r17 [15] ENUMERATED { supported(0) } OPTIONAL,
     -- R1 24-5f: Enhanced PDCCH monitoring for 960KHz in FR2-2
   enhancedPDCCH-monitoringSCS-960kHz-r17 [16] SEQUENCE {
      pdcch-monitoring4-1-r17 [0] ENUMERATED { supported(0) } OPTIONAL,
      pdcch-monitoring4-2-r17 [1] ENUMERATED { supported(0) } OPTIONAL,
      pdcch-monitoring8-4-r17 [2] ENUMERATED { supported(0) } OPTIONAL
   } OPTIONAL,
     -- R1 24-6: Type 1 channel access procedure in uplink for FR2-2 with shared spectrum channel access
   type1-ChannelAccess-FR2-2-r17 [17] ENUMERATED { supported(0) } OPTIONAL,
     -- R1 24-7: Type 2 channel access procedure in uplink for FR2-2 with shared spectrum channel access
   type2-ChannelAccess-FR2-2-r17 [18] ENUMERATED { supported(0) } OPTIONAL,
     -- R1 24-10: Reduced beam switching time delay
   reduced-BeamSwitchTiming-FR2-2-r17 [19] ENUMERATED { supported(0) } OPTIONAL
      ,
     -- R1 24-8: 32 DL HARQ processes for FR 2-2
   support32-DL-HARQ-ProcessPerSCS-r17 [20] SEQUENCE {
      scs-120kHz-r17 [0] ENUMERATED { supported(0) } OPTIONAL,
      scs-480kHz-r17 [1] ENUMERATED { supported(0) } OPTIONAL,
      scs-960kHz-r17 [2] ENUMERATED { supported(0) } OPTIONAL
   } OPTIONAL,
     -- R1 24-9: 32 UL HARQ processes for FR 2-2
   support32-UL-HARQ-ProcessPerSCS-r17 [21] SEQUENCE {
      scs-120kHz-r17 [0] ENUMERATED { supported(0) } OPTIONAL,
      scs-480kHz-r17 [1] ENUMERATED { supported(0) } OPTIONAL,
      scs-960kHz-r17 [2] ENUMERATED { supported(0) } OPTIONAL
   } OPTIONAL,
   ...,
   [[
      modulation64-QAM-PUSCH-FR2-2-r17 [22] ENUMERATED { supported(0) }
          OPTIONAL
   ]]
}

-- TAG-FR2-2-ACCESSPARAMSPERBAND-STOP
-- TAG-HIGHSPEEDPARAMETERS-START
HighSpeedParameters-r16 ::= SEQUENCE {
   measurementEnhancement-r16 [0] ENUMERATED { supported(0) } OPTIONAL,
   demodulationEnhancement-r16 [1] ENUMERATED { supported(0) } OPTIONAL
}

HighSpeedParameters-v1650 ::= CHOICE {
   intraNR-MeasurementEnhancement-r16 [0] ENUMERATED { supported(0) },
   interRAT-MeasurementEnhancement-r16 [1] ENUMERATED { supported(0) }
}

HighSpeedParameters-v1700 ::= SEQUENCE {
     -- R4 18-1: Enhanced RRM requirements specified for CA for FR1 HST
   measurementEnhancementCA-r17 [0] ENUMERATED { supported(0) } OPTIONAL,
     -- R4 18-2: Enhanced RRM requirements specified for inter-frequency measurement in connected mode for FR1 HST
   measurementEnhancementInterFreq-r17 [1] ENUMERATED { supported(0) } OPTIONAL
}

IMS-ParametersCommon ::= SEQUENCE {
   voiceOverEUTRA-5GC [0] ENUMERATED { supported(0) } OPTIONAL,
   ...,
   [[
      voiceOverSCG-BearerEUTRA-5GC [1] ENUMERATED { supported(0) } OPTIONAL
   ]],
   [[
      voiceFallbackIndicationEPS-r16 [2] ENUMERATED { supported(0) } OPTIONAL
   ]]
}

IMS-ParametersFRX-Diff ::= SEQUENCE {
   voiceOverNR [0] ENUMERATED { supported(0) } OPTIONAL,
   ...
}

-- TAG-HIGHSPEEDPARAMETERS-STOP
-- TAG-IMS-PARAMETERS-START
IMS-Parameters ::= SEQUENCE {
   ims-ParametersCommon [0] IMS-ParametersCommon OPTIONAL,
   ims-ParametersFRX-Diff [1] IMS-ParametersFRX-Diff OPTIONAL,
   ...
}

IMS-ParametersFR2-2-r17 ::= SEQUENCE {
   voiceOverNR-r17 [0] ENUMERATED { supported(0) } OPTIONAL,
   ...
}

IMS-Parameters-v1700 ::= SEQUENCE {
   ims-ParametersFR2-2-r17 [0] IMS-ParametersFR2-2-r17 OPTIONAL
}

EUTRA-ParametersCommon ::= SEQUENCE {
   mfbi-EUTRA [0] ENUMERATED { supported(0) } OPTIONAL,
   modifiedMPR-BehaviorEUTRA [1] BIT STRING  (SIZE (32)) OPTIONAL,
   multiNS-Pmax-EUTRA [2] ENUMERATED { supported(0) } OPTIONAL,
   rs-SINR-MeasEUTRA [3] ENUMERATED { supported(0) } OPTIONAL,
   ...,
   [[
      ne-DC [4] ENUMERATED { supported(0) } OPTIONAL
   ]],
   [[
      nr-HO-ToEN-DC-r16 [5] ENUMERATED { supported(0) } OPTIONAL
   ]]
}

EUTRA-ParametersXDD-Diff ::= SEQUENCE {
   rsrqMeasWidebandEUTRA [0] ENUMERATED { supported(0) } OPTIONAL,
   ...
}

EUTRA-Parameters ::= SEQUENCE {
   supportedBandListEUTRA [0] SEQUENCE (SIZE (1..maxBandsEUTRA)) OF FreqBandIndicatorEUTRA,
   eutra-ParametersCommon [1] EUTRA-ParametersCommon OPTIONAL,
   eutra-ParametersXDD-Diff [2] EUTRA-ParametersXDD-Diff OPTIONAL,
   ...
}

UTRA-FDD-Parameters-r16 ::= SEQUENCE {
   supportedBandListUTRA-FDD-r16 [0] SEQUENCE (SIZE (1..maxBandsUTRA-FDD-r16)) OF 
      SupportedBandUTRA-FDD-r16,
   ...
}

-- TAG-IMS-PARAMETERS-STOP
-- TAG-INTERRAT-PARAMETERS-START
InterRAT-Parameters ::= SEQUENCE {
   eutra [0] EUTRA-Parameters OPTIONAL,
   ...,
   [[
      utra-FDD-r16 [1] UTRA-FDD-Parameters-r16 OPTIONAL
   ]]
}

MAC-ParametersCommon ::= SEQUENCE {
   lcp-Restriction [0] ENUMERATED { supported(0) } OPTIONAL,
   dummy [1] ENUMERATED { supported(0) } OPTIONAL,
   lch-ToSCellRestriction [2] ENUMERATED { supported(0) } OPTIONAL,
   ...,
   [[
      recommendedBitRate [3] ENUMERATED { supported(0) } OPTIONAL,
      recommendedBitRateQuery [4] ENUMERATED { supported(0) } OPTIONAL
   ]],
   [[
      recommendedBitRateMultiplier-r16 [5] ENUMERATED { supported(0) } OPTIONAL
         ,
      preEmptiveBSR-r16 [6] ENUMERATED { supported(0) } OPTIONAL,
      autonomousTransmission-r16 [7] ENUMERATED { supported(0) } OPTIONAL,
      lch-PriorityBasedPrioritization-r16 [8] ENUMERATED { supported(0) }
          OPTIONAL,
      lch-ToConfiguredGrantMapping-r16 [9] ENUMERATED { supported(0) } OPTIONAL
         ,
      lch-ToGrantPriorityRestriction-r16 [10] ENUMERATED { supported(0) }
          OPTIONAL,
      singlePHR-P-r16 [11] ENUMERATED { supported(0) } OPTIONAL,
      ul-LBT-FailureDetectionRecovery-r16 [12] ENUMERATED { supported(0) }
          OPTIONAL,
      tdd-MPE-P-MPR-Reporting-r16 [13] ENUMERATED { supported(0) } OPTIONAL,
      lcid-ExtensionIAB-r16 [14] ENUMERATED { supported(0) } OPTIONAL
   ]],
   [[
      spCell-BFR-CBRA-r16 [15] ENUMERATED { supported(0) } OPTIONAL
   ]],
   [[
      srs-ResourceId-Ext-r16 [16] ENUMERATED { supported(0) } OPTIONAL
   ]],
   [[
      enhancedUuDRX-forSidelink-r17 [17] ENUMERATED { supported(0) } OPTIONAL,
      mg-ActivationRequestPRS-Meas-r17 [18] ENUMERATED { supported(0) }
          OPTIONAL,
      mg-ActivationCommPRS-Meas-r17 [19] ENUMERATED { supported(0) } OPTIONAL,
      intraCG-Prioritization-r17 [20] ENUMERATED { supported(0) } OPTIONAL,
      jointPrioritizationCG-Retx-Timer-r17 [21] ENUMERATED { supported(0) }
          OPTIONAL,
      survivalTime-r17 [22] ENUMERATED { supported(0) } OPTIONAL,
      lcg-ExtensionIAB-r17 [23] ENUMERATED { supported(0) } OPTIONAL,
      harq-FeedbackDisabled-r17 [24] ENUMERATED { supported(0) } OPTIONAL,
      uplink-Harq-ModeB-r17 [25] ENUMERATED { supported(0) } OPTIONAL,
      sr-TriggeredBy-TA-Report-r17 [26] ENUMERATED { supported(0) } OPTIONAL,
      extendedDRX-CycleInactive-r17 [27] ENUMERATED { supported(0) } OPTIONAL,
      simultaneousSR-PUSCH-DiffPUCCH-groups-r17 [28] ENUMERATED { supported(0)
          } OPTIONAL,
      lastTransmissionUL-r17 [29] ENUMERATED { supported(0) } OPTIONAL
   ]]
}

MAC-ParametersXDD-Diff ::= SEQUENCE {
   skipUplinkTxDynamic [0] ENUMERATED { supported(0) } OPTIONAL,
   logicalChannelSR-DelayTimer [1] ENUMERATED { supported(0) } OPTIONAL,
   longDRX-Cycle [2] ENUMERATED { supported(0) } OPTIONAL,
   shortDRX-Cycle [3] ENUMERATED { supported(0) } OPTIONAL,
   multipleSR-Configurations [4] ENUMERATED { supported(0) } OPTIONAL,
   multipleConfiguredGrants [5] ENUMERATED { supported(0) } OPTIONAL,
   ...,
   [[
      secondaryDRX-Group-r16 [6] ENUMERATED { supported(0) } OPTIONAL
   ]],
   [[
      enhancedSkipUplinkTxDynamic-r16 [7] ENUMERATED { supported(0) } OPTIONAL
         ,
      enhancedSkipUplinkTxConfigured-r16 [8] ENUMERATED { supported(0) }
          OPTIONAL
   ]]
}

-- TAG-INTERRAT-PARAMETERS-STOP
-- TAG-MAC-PARAMETERS-START
MAC-Parameters ::= SEQUENCE {
   mac-ParametersCommon [0] MAC-ParametersCommon OPTIONAL,
   mac-ParametersXDD-Diff [1] MAC-ParametersXDD-Diff OPTIONAL
}

MinTimeGap-r16 ::= SEQUENCE {
   scs-15kHz-r16 [0] ENUMERATED { sl1(0), sl3(1) } OPTIONAL,
   scs-30kHz-r16 [1] ENUMERATED { sl1(0), sl6(1) } OPTIONAL,
   scs-60kHz-r16 [2] ENUMERATED { sl1(0), sl12(1) } OPTIONAL,
   scs-120kHz-r16 [3] ENUMERATED { sl2(0), sl24(1) } OPTIONAL
}

MAC-ParametersFRX-Diff-r16 ::= SEQUENCE {
   directMCG-SCellActivation-r16 [0] ENUMERATED { supported(0) } OPTIONAL,
   directMCG-SCellActivationResume-r16 [1] ENUMERATED { supported(0) } OPTIONAL
      ,
   directSCG-SCellActivation-r16 [2] ENUMERATED { supported(0) } OPTIONAL,
   directSCG-SCellActivationResume-r16 [3] ENUMERATED { supported(0) } OPTIONAL
      ,
     -- R1 19-1: DRX Adaptation
   drx-Adaptation-r16 [4] SEQUENCE {
      non-SharedSpectrumChAccess-r16 [0] MinTimeGap-r16 OPTIONAL,
      sharedSpectrumChAccess-r16 [1] MinTimeGap-r16 OPTIONAL
   } OPTIONAL,
   ...
}

MAC-Parameters-v1610 ::= SEQUENCE {
   mac-ParametersFRX-Diff-r16 [0] MAC-ParametersFRX-Diff-r16 OPTIONAL
}

MinTimeGapFR2-2-r17 ::= SEQUENCE {
   scs-120kHz-r17 [0] ENUMERATED { sl2(0), sl24(1) } OPTIONAL,
   scs-480kHz-r17 [1] ENUMERATED { sl8(0), sl96(1) } OPTIONAL,
   scs-960kHz-r17 [2] ENUMERATED { sl16(0), sl192(1) } OPTIONAL
}

MAC-ParametersFR2-2-r17 ::= SEQUENCE {
   directMCG-SCellActivation-r17 [0] ENUMERATED { supported(0) } OPTIONAL,
   directMCG-SCellActivationResume-r17 [1] ENUMERATED { supported(0) } OPTIONAL
      ,
   directSCG-SCellActivation-r17 [2] ENUMERATED { supported(0) } OPTIONAL,
   directSCG-SCellActivationResume-r17 [3] ENUMERATED { supported(0) } OPTIONAL
      ,
   drx-Adaptation-r17 [4] SEQUENCE {
      non-SharedSpectrumChAccess-r17 [0] MinTimeGapFR2-2-r17 OPTIONAL,
      sharedSpectrumChAccess-r17 [1] MinTimeGapFR2-2-r17 OPTIONAL
   } OPTIONAL,
   ...
}

MAC-Parameters-v1700 ::= SEQUENCE {
   mac-ParametersFR2-2-r17 [0] MAC-ParametersFR2-2-r17 OPTIONAL
}

MeasAndMobParametersCommon ::= SEQUENCE {
   supportedGapPattern [0] BIT STRING  (SIZE (22)) OPTIONAL,
   ssb-RLM [1] ENUMERATED { supported(0) } OPTIONAL,
   ssb-AndCSI-RS-RLM [2] ENUMERATED { supported(0) } OPTIONAL,
   ...,
   [[
      eventB-MeasAndReport [3] ENUMERATED { supported(0) } OPTIONAL,
      handoverFDD-TDD [4] ENUMERATED { supported(0) } OPTIONAL,
      eutra-CGI-Reporting [5] ENUMERATED { supported(0) } OPTIONAL,
      nr-CGI-Reporting [6] ENUMERATED { supported(0) } OPTIONAL
   ]],
   [[
      independentGapConfig [7] ENUMERATED { supported(0) } OPTIONAL,
      periodicEUTRA-MeasAndReport [8] ENUMERATED { supported(0) } OPTIONAL,
      handoverFR1-FR2 [9] ENUMERATED { supported(0) } OPTIONAL,
      maxNumberCSI-RS-RRM-RS-SINR [10] ENUMERATED { n4(0), n8(1), n16(2), 
         n32(3), n64(4), n96(5) } OPTIONAL
   ]],
   [[
      nr-CGI-Reporting-ENDC [11] ENUMERATED { supported(0) } OPTIONAL
   ]],
   [[
      eutra-CGI-Reporting-NEDC [12] ENUMERATED { supported(0) } OPTIONAL,
      eutra-CGI-Reporting-NRDC [13] ENUMERATED { supported(0) } OPTIONAL,
      nr-CGI-Reporting-NEDC [14] ENUMERATED { supported(0) } OPTIONAL,
      nr-CGI-Reporting-NRDC [15] ENUMERATED { supported(0) } OPTIONAL
   ]],
   [[
      reportAddNeighMeasForPeriodic-r16 [16] ENUMERATED { supported(0) }
          OPTIONAL,
      condHandoverParametersCommon-r16 [17] SEQUENCE {
         condHandoverFDD-TDD-r16 [0] ENUMERATED { supported(0) } OPTIONAL,
         condHandoverFR1-FR2-r16 [1] ENUMERATED { supported(0) } OPTIONAL
      } OPTIONAL,
      nr-NeedForGap-Reporting-r16 [18] ENUMERATED { supported(0) } OPTIONAL,
      supportedGapPattern-NRonly-r16 [19] BIT STRING  (SIZE (10)) OPTIONAL,
      supportedGapPattern-NRonly-NEDC-r16 [20] ENUMERATED { supported(0) }
          OPTIONAL,
      maxNumberCLI-RSSI-r16 [21] ENUMERATED { n8(0), n16(1), n32(2), n64(3) }
          OPTIONAL,
      maxNumberCLI-SRS-RSRP-r16 [22] ENUMERATED { n4(0), n8(1), n16(2), n32(3)
          } OPTIONAL,
      maxNumberPerSlotCLI-SRS-RSRP-r16 [23] ENUMERATED { n2(0), n4(1), n8(2) }
          OPTIONAL,
      mfbi-IAB-r16 [24] ENUMERATED { supported(0) } OPTIONAL,
      dummy [25] ENUMERATED { supported(0) } OPTIONAL,
      nr-CGI-Reporting-NPN-r16 [26] ENUMERATED { supported(0) } OPTIONAL,
      idleInactiveEUTRA-MeasReport-r16 [27] ENUMERATED { supported(0) }
          OPTIONAL,
      idleInactive-ValidityArea-r16 [28] ENUMERATED { supported(0) } OPTIONAL,
      eutra-AutonomousGaps-r16 [29] ENUMERATED { supported(0) } OPTIONAL,
      eutra-AutonomousGaps-NEDC-r16 [30] ENUMERATED { supported(0) } OPTIONAL,
      eutra-AutonomousGaps-NRDC-r16 [31] ENUMERATED { supported(0) } OPTIONAL,
      pcellT312-r16 [32] ENUMERATED { supported(0) } OPTIONAL,
      supportedGapPattern-r16 [33] BIT STRING  (SIZE (2)) OPTIONAL
   ]],
   [[
      concurrentMeasGap-r17 [34] EXPLICIT CHOICE {
         concurrentPerUE-OnlyMeasGap-r17 [0] ENUMERATED { supported(0) },
         concurrentPerUE-PerFRCombMeasGap-r17 [1] ENUMERATED { supported(0) }
      } OPTIONAL,
      nr-NeedForGapNCSG-Reporting-r17 [35] ENUMERATED { supported(0) } OPTIONAL
         ,
      eutra-NeedForGapNCSG-Reporting-r17 [36] ENUMERATED { supported(0) }
          OPTIONAL,
      ncsg-MeasGapPerFR-r17 [37] ENUMERATED { supported(0) } OPTIONAL,
      ncsg-MeasGapPatterns-r17 [38] BIT STRING  (SIZE (24)) OPTIONAL,
      ncsg-MeasGapNR-Patterns-r17 [39] BIT STRING  (SIZE (24)) OPTIONAL,
      preconfiguredUE-AutonomousMeasGap-r17 [40] ENUMERATED { supported(0) }
          OPTIONAL,
      preconfiguredNW-ControlledMeasGap-r17 [41] ENUMERATED { supported(0) }
          OPTIONAL,
      handoverFR1-FR2-2-r17 [42] ENUMERATED { supported(0) } OPTIONAL,
      handoverFR2-1-FR2-2-r17 [43] ENUMERATED { supported(0) } OPTIONAL,
      independentGapConfigPRS-r17 [44] ENUMERATED { supported(0) } OPTIONAL,
      rrm-RelaxationRRC-ConnectedRedCap-r17 [45] ENUMERATED { supported(0) }
          OPTIONAL,
      parallelMeasurementGap-r17 [46] ENUMERATED { n2(0) } OPTIONAL,
      condHandoverWithSCG-NRDC-r17 [47] ENUMERATED { supported(0) } OPTIONAL,
      gNB-ID-LengthReporting-r17 [48] ENUMERATED { supported(0) } OPTIONAL,
      gNB-ID-LengthReporting-ENDC-r17 [49] ENUMERATED { supported(0) } OPTIONAL
         ,
      gNB-ID-LengthReporting-NEDC-r17 [50] ENUMERATED { supported(0) } OPTIONAL
         ,
      gNB-ID-LengthReporting-NRDC-r17 [51] ENUMERATED { supported(0) } OPTIONAL
         ,
      gNB-ID-LengthReporting-NPN-r17 [52] ENUMERATED { supported(0) } OPTIONAL
   ]],
   [[
      parallelSMTC-r17 [53] ENUMERATED { n4(0) } OPTIONAL,
      concurrentMeasGapEUTRA-r17 [54] ENUMERATED { supported(0) } OPTIONAL,
      serviceLinkPropDelayDiffReporting-r17 [55] ENUMERATED { supported(0) }
          OPTIONAL,
      ncsg-SymbolLevelScheduleRestrictionInter-r17 [56] ENUMERATED { 
         supported(0) } OPTIONAL
   ]],
   [[
      eventD1-MeasReportTrigger-r17 [57] ENUMERATED { supported(0) } OPTIONAL,
      independentGapConfig-maxCC-r17 [58] SEQUENCE {
         fr1-Only-r17 [0] INTEGER (1..32) OPTIONAL,
         fr2-Only-r17 [1] INTEGER (1..32) OPTIONAL,
         fr1-AndFR2-r17 [2] INTEGER (1..32) OPTIONAL
      } OPTIONAL
   ]],
   [[
      interSatMeas-r17 [59] ENUMERATED { supported(0) } OPTIONAL,
      deriveSSB-IndexFromCellInterNon-NCSG-r17 [60] ENUMERATED { supported(0) }
          OPTIONAL
   ]]
}

MeasAndMobParametersXDD-Diff ::= SEQUENCE {
   intraAndInterF-MeasAndReport [0] ENUMERATED { supported(0) } OPTIONAL,
   eventA-MeasAndReport [1] ENUMERATED { supported(0) } OPTIONAL,
   ...,
   [[
      handoverInterF [2] ENUMERATED { supported(0) } OPTIONAL,
      handoverLTE-EPC [3] ENUMERATED { supported(0) } OPTIONAL,
      handoverLTE-5GC [4] ENUMERATED { supported(0) } OPTIONAL
   ]],
   [[
      sftd-MeasNR-Neigh [5] ENUMERATED { supported(0) } OPTIONAL,
      sftd-MeasNR-Neigh-DRX [6] ENUMERATED { supported(0) } OPTIONAL
   ]],
   [[
      dummy [7] ENUMERATED { supported(0) } OPTIONAL
   ]]
}

MeasAndMobParametersFRX-Diff ::= SEQUENCE {
   ss-SINR-Meas [0] ENUMERATED { supported(0) } OPTIONAL,
   csi-RSRP-AndRSRQ-MeasWithSSB [1] ENUMERATED { supported(0) } OPTIONAL,
   csi-RSRP-AndRSRQ-MeasWithoutSSB [2] ENUMERATED { supported(0) } OPTIONAL,
   csi-SINR-Meas [3] ENUMERATED { supported(0) } OPTIONAL,
   csi-RS-RLM [4] ENUMERATED { supported(0) } OPTIONAL,
   ...,
   [[
      handoverInterF [5] ENUMERATED { supported(0) } OPTIONAL,
      handoverLTE-EPC [6] ENUMERATED { supported(0) } OPTIONAL,
      handoverLTE-5GC [7] ENUMERATED { supported(0) } OPTIONAL
   ]],
   [[
      maxNumberResource-CSI-RS-RLM [8] ENUMERATED { n2(0), n4(1), n6(2), n8(3)
          } OPTIONAL
   ]],
   [[
      simultaneousRxDataSSB-DiffNumerology [9] ENUMERATED { supported(0) }
          OPTIONAL
   ]],
   [[
      nr-AutonomousGaps-r16 [10] ENUMERATED { supported(0) } OPTIONAL,
      nr-AutonomousGaps-ENDC-r16 [11] ENUMERATED { supported(0) } OPTIONAL,
      nr-AutonomousGaps-NEDC-r16 [12] ENUMERATED { supported(0) } OPTIONAL,
      nr-AutonomousGaps-NRDC-r16 [13] ENUMERATED { supported(0) } OPTIONAL,
      dummy [14] ENUMERATED { supported(0) } OPTIONAL,
      cli-RSSI-Meas-r16 [15] ENUMERATED { supported(0) } OPTIONAL,
      cli-SRS-RSRP-Meas-r16 [16] ENUMERATED { supported(0) } OPTIONAL,
      interFrequencyMeas-NoGap-r16 [17] ENUMERATED { supported(0) } OPTIONAL,
      simultaneousRxDataSSB-DiffNumerology-Inter-r16 [18] ENUMERATED { 
         supported(0) } OPTIONAL,
      idleInactiveNR-MeasReport-r16 [19] ENUMERATED { supported(0) } OPTIONAL,
      idleInactiveNR-MeasBeamReport-r16 [20] ENUMERATED { supported(0) }
          OPTIONAL
   ]],
   [[
      increasedNumberofCSIRSPerMO-r16 [21] ENUMERATED { supported(0) } OPTIONAL
   ]]
}

-- TAG-MAC-PARAMETERS-STOP
-- TAG-MEASANDMOBPARAMETERS-START
MeasAndMobParameters ::= SEQUENCE {
   measAndMobParametersCommon [0] MeasAndMobParametersCommon OPTIONAL,
   measAndMobParametersXDD-Diff [1] MeasAndMobParametersXDD-Diff OPTIONAL,
   measAndMobParametersFRX-Diff [2] MeasAndMobParametersFRX-Diff OPTIONAL
}

MeasAndMobParametersFR2-2-r17 ::= SEQUENCE {
   handoverInterF-r17 [0] ENUMERATED { supported(0) } OPTIONAL,
   handoverLTE-EPC-r17 [1] ENUMERATED { supported(0) } OPTIONAL,
   handoverLTE-5GC-r17 [2] ENUMERATED { supported(0) } OPTIONAL,
   idleInactiveNR-MeasReport-r17 [3] ENUMERATED { supported(0) } OPTIONAL,
   ...
}

MeasAndMobParameters-v1700 ::= SEQUENCE {
   measAndMobParametersFR2-2-r17 [0] MeasAndMobParametersFR2-2-r17 OPTIONAL
}

MeasAndMobParametersMRDC-Common ::= SEQUENCE {
   independentGapConfig [0] ENUMERATED { supported(0) } OPTIONAL
}

MeasAndMobParametersMRDC-XDD-Diff ::= SEQUENCE {
   sftd-MeasPSCell [0] ENUMERATED { supported(0) } OPTIONAL,
   sftd-MeasNR-Cell [1] ENUMERATED { supported(0) } OPTIONAL
}

MeasAndMobParametersMRDC-FRX-Diff ::= SEQUENCE {
   simultaneousRxDataSSB-DiffNumerology [0] ENUMERATED { supported(0) }
       OPTIONAL
}

-- TAG-MEASANDMOBPARAMETERS-STOP
-- TAG-MEASANDMOBPARAMETERSMRDC-START
MeasAndMobParametersMRDC ::= SEQUENCE {
   measAndMobParametersMRDC-Common [0] MeasAndMobParametersMRDC-Common OPTIONAL
      ,
   measAndMobParametersMRDC-XDD-Diff [1] MeasAndMobParametersMRDC-XDD-Diff
       OPTIONAL,
   measAndMobParametersMRDC-FRX-Diff [2] MeasAndMobParametersMRDC-FRX-Diff
       OPTIONAL
}

MeasAndMobParametersMRDC-XDD-Diff-v1560 ::= SEQUENCE {
   sftd-MeasPSCell-NEDC [0] ENUMERATED { supported(0) } OPTIONAL
}

MeasAndMobParametersMRDC-v1560 ::= SEQUENCE {
   measAndMobParametersMRDC-XDD-Diff-v1560 [0] 
      MeasAndMobParametersMRDC-XDD-Diff-v1560 OPTIONAL
}

MeasAndMobParametersMRDC-Common-v1610 ::= SEQUENCE {
   condPSCellChangeParametersCommon-r16 [0] SEQUENCE {
      condPSCellChangeFDD-TDD-r16 [0] ENUMERATED { supported(0) } OPTIONAL,
      condPSCellChangeFR1-FR2-r16 [1] ENUMERATED { supported(0) } OPTIONAL
   } OPTIONAL,
   pscellT312-r16 [1] ENUMERATED { supported(0) } OPTIONAL
}

MeasAndMobParametersMRDC-v1610 ::= SEQUENCE {
   measAndMobParametersMRDC-Common-v1610 [0] 
      MeasAndMobParametersMRDC-Common-v1610 OPTIONAL,
   interNR-MeasEUTRA-IAB-r16 [1] ENUMERATED { supported(0) } OPTIONAL
}

MeasAndMobParametersMRDC-Common-v1700 ::= SEQUENCE {
   condPSCellChangeParameters-r17 [0] SEQUENCE {
      inter-SN-condPSCellChangeFDD-TDD-NRDC-r17 [0] ENUMERATED { supported(0) }
          OPTIONAL,
      inter-SN-condPSCellChangeFR1-FR2-NRDC-r17 [1] ENUMERATED { supported(0) }
          OPTIONAL,
      inter-SN-condPSCellChangeFDD-TDD-ENDC-r17 [2] ENUMERATED { supported(0) }
          OPTIONAL,
      inter-SN-condPSCellChangeFR1-FR2-ENDC-r17 [3] ENUMERATED { supported(0) }
          OPTIONAL,
      mn-InitiatedCondPSCellChange-FR1FDD-ENDC-r17 [4] ENUMERATED { 
         supported(0) } OPTIONAL,
      mn-InitiatedCondPSCellChange-FR1TDD-ENDC-r17 [5] ENUMERATED { 
         supported(0) } OPTIONAL,
      mn-InitiatedCondPSCellChange-FR2TDD-ENDC-r17 [6] ENUMERATED { 
         supported(0) } OPTIONAL,
      sn-InitiatedCondPSCellChange-FR1FDD-ENDC-r17 [7] ENUMERATED { 
         supported(0) } OPTIONAL,
      sn-InitiatedCondPSCellChange-FR1TDD-ENDC-r17 [8] ENUMERATED { 
         supported(0) } OPTIONAL,
      sn-InitiatedCondPSCellChange-FR2TDD-ENDC-r17 [9] ENUMERATED { 
         supported(0) } OPTIONAL
   } OPTIONAL,
   condHandoverWithSCG-ENDC-r17 [1] ENUMERATED { supported(0) } OPTIONAL,
   condHandoverWithSCG-NEDC-r17 [2] ENUMERATED { supported(0) } OPTIONAL
}

MeasAndMobParametersMRDC-v1700 ::= SEQUENCE {
   measAndMobParametersMRDC-Common-v1700 [0] 
      MeasAndMobParametersMRDC-Common-v1700 OPTIONAL
}

MeasAndMobParametersMRDC-Common-v1730 ::= SEQUENCE {
   independentGapConfig-maxCC-r17 [0] SEQUENCE {
      fr1-Only-r17 [0] INTEGER (1..32) OPTIONAL,
      fr2-Only-r17 [1] INTEGER (1..32) OPTIONAL,
      fr1-AndFR2-r17 [2] INTEGER (1..32) OPTIONAL
   }
}

MeasAndMobParametersMRDC-v1730 ::= SEQUENCE {
   measAndMobParametersMRDC-Common-v1730 [0] 
      MeasAndMobParametersMRDC-Common-v1730 OPTIONAL
}

DummyG ::= SEQUENCE {
   maxNumberSSB-CSI-RS-ResourceOneTx [0] ENUMERATED { n8(0), n16(1), n32(2), 
      n64(3) },
   maxNumberSSB-CSI-RS-ResourceTwoTx [1] ENUMERATED { n0(0), n4(1), n8(2), 
      n16(3), n32(4), n64(5) },
   supportedCSI-RS-Density [2] ENUMERATED { one(0), three(1), oneAndThree(2) }
}

PTRS-DensityRecommendationDL ::= SEQUENCE {
   frequencyDensity1 [0] INTEGER (1..276),
   frequencyDensity2 [1] INTEGER (1..276),
   timeDensity1 [2] INTEGER (0..29),
   timeDensity2 [3] INTEGER (0..29),
   timeDensity3 [4] INTEGER (0..29)
}

PTRS-DensityRecommendationUL ::= SEQUENCE {
   frequencyDensity1 [0] INTEGER (1..276),
   frequencyDensity2 [1] INTEGER (1..276),
   timeDensity1 [2] INTEGER (0..29),
   timeDensity2 [3] INTEGER (0..29),
   timeDensity3 [4] INTEGER (0..29),
   sampleDensity1 [5] INTEGER (1..276),
   sampleDensity2 [6] INTEGER (1..276),
   sampleDensity3 [7] INTEGER (1..276),
   sampleDensity4 [8] INTEGER (1..276),
   sampleDensity5 [9] INTEGER (1..276)
}

DummyH ::= SEQUENCE {
   burstLength [0] INTEGER (1..2),
   maxSimultaneousResourceSetsPerCC [1] INTEGER (1..8),
   maxConfiguredResourceSetsPerCC [2] INTEGER (1..64),
   maxConfiguredResourceSetsAllCC [3] INTEGER (1..128)
}

BeamManagementSSB-CSI-RS ::= SEQUENCE {
   maxNumberSSB-CSI-RS-ResourceOneTx [0] ENUMERATED { n0(0), n8(1), n16(2), 
      n32(3), n64(4) },
   maxNumberCSI-RS-Resource [1] ENUMERATED { n0(0), n4(1), n8(2), n16(3), 
      n32(4), n64(5) },
   maxNumberCSI-RS-ResourceTwoTx [2] ENUMERATED { n0(0), n4(1), n8(2), n16(3), 
      n32(4), n64(5) },
   supportedCSI-RS-Density [3] ENUMERATED { one(0), three(1), oneAndThree(2) }
       OPTIONAL,
   maxNumberAperiodicCSI-RS-Resource [4] ENUMERATED { n0(0), n1(1), n4(2), 
      n8(3), n16(4), n32(5), n64(6) }
}

CSI-RS-IM-ReceptionForFeedback ::= SEQUENCE {
   maxConfigNumberNZP-CSI-RS-PerCC [0] INTEGER (1..64),
   maxConfigNumberPortsAcrossNZP-CSI-RS-PerCC [1] INTEGER (2..256),
   maxConfigNumberCSI-IM-PerCC [2] ENUMERATED { n1(0), n2(1), n4(2), n8(3), 
      n16(4), n32(5) },
   maxNumberSimultaneousNZP-CSI-RS-PerCC [3] INTEGER (1..64),
   totalNumberPortsSimultaneousNZP-CSI-RS-PerCC [4] INTEGER (2..256)
}

CSI-RS-ProcFrameworkForSRS ::= SEQUENCE {
   maxNumberPeriodicSRS-AssocCSI-RS-PerBWP [0] INTEGER (1..4),
   maxNumberAperiodicSRS-AssocCSI-RS-PerBWP [1] INTEGER (1..4),
   maxNumberSP-SRS-AssocCSI-RS-PerBWP [2] INTEGER (0..4),
   simultaneousSRS-AssocCSI-RS-PerCC [3] INTEGER (1..8)
}

CSI-ReportFramework ::= SEQUENCE {
   maxNumberPeriodicCSI-PerBWP-ForCSI-Report [0] INTEGER (1..4),
   maxNumberAperiodicCSI-PerBWP-ForCSI-Report [1] INTEGER (1..4),
   maxNumberSemiPersistentCSI-PerBWP-ForCSI-Report [2] INTEGER (0..4),
   maxNumberPeriodicCSI-PerBWP-ForBeamReport [3] INTEGER (1..4),
   maxNumberAperiodicCSI-PerBWP-ForBeamReport [4] INTEGER (1..4),
   maxNumberAperiodicCSI-triggeringStatePerCC [5] ENUMERATED { n3(0), n7(1), 
      n15(2), n31(3), n63(4), n128(5) },
   maxNumberSemiPersistentCSI-PerBWP-ForBeamReport [6] INTEGER (0..4),
   simultaneousCSI-ReportsPerCC [7] INTEGER (1..8)
}

CSI-RS-ForTracking ::= SEQUENCE {
   maxBurstLength [0] INTEGER (1..2),
   maxSimultaneousResourceSetsPerCC [1] INTEGER (1..8),
   maxConfiguredResourceSetsPerCC [2] INTEGER (1..64),
   maxConfiguredResourceSetsAllCC [3] INTEGER (1..256)
}

SpatialRelations ::= SEQUENCE {
   maxNumberConfiguredSpatialRelations [0] ENUMERATED { n4(0), n8(1), n16(2), 
      n32(3), n64(4), n96(5) },
   maxNumberActiveSpatialRelations [1] ENUMERATED { n1(0), n2(1), n4(2), n8(3)
      , n14(4) },
   additionalActiveSpatialRelationPUCCH [2] ENUMERATED { supported(0) }
       OPTIONAL,
   maxNumberDL-RS-QCL-TypeD [3] ENUMERATED { n1(0), n2(1), n4(2), n8(3), n14(4)
       }
}

CSI-ReportFrameworkExt-r16 ::= SEQUENCE {
   maxNumberAperiodicCSI-PerBWP-ForCSI-ReportExt-r16 [0] INTEGER (5..8)
}

-- TAG-MIMO-LAYERS-STOP
-- TAG-MIMO-PARAMETERSPERBAND-START
MIMO-ParametersPerBand ::= SEQUENCE {
   tci-StatePDSCH [0] SEQUENCE {
      maxNumberConfiguredTCI-StatesPerCC [0] ENUMERATED { n4(0), n8(1), n16(2)
         , n32(3), n64(4), n128(5) } OPTIONAL,
      maxNumberActiveTCI-PerBWP [1] ENUMERATED { n1(0), n2(1), n4(2), n8(3) }
          OPTIONAL
   } OPTIONAL,
   additionalActiveTCI-StatePDCCH [1] ENUMERATED { supported(0) } OPTIONAL,
   pusch-TransCoherence [2] ENUMERATED { nonCoherent(0), partialCoherent(1), 
      fullCoherent(2) } OPTIONAL,
   beamCorrespondenceWithoutUL-BeamSweeping [3] ENUMERATED { supported(0) }
       OPTIONAL,
   periodicBeamReport [4] ENUMERATED { supported(0) } OPTIONAL,
   aperiodicBeamReport [5] ENUMERATED { supported(0) } OPTIONAL,
   sp-BeamReportPUCCH [6] ENUMERATED { supported(0) } OPTIONAL,
   sp-BeamReportPUSCH [7] ENUMERATED { supported(0) } OPTIONAL,
   dummy1 [8] DummyG OPTIONAL,
   maxNumberRxBeam [9] INTEGER (2..8) OPTIONAL,
   maxNumberRxTxBeamSwitchDL [10] SEQUENCE {
      scs-15kHz [0] ENUMERATED { n4(0), n7(1), n14(2) } OPTIONAL,
      scs-30kHz [1] ENUMERATED { n4(0), n7(1), n14(2) } OPTIONAL,
      scs-60kHz [2] ENUMERATED { n4(0), n7(1), n14(2) } OPTIONAL,
      scs-120kHz [3] ENUMERATED { n4(0), n7(1), n14(2) } OPTIONAL,
      scs-240kHz [4] ENUMERATED { n4(0), n7(1), n14(2) } OPTIONAL
   } OPTIONAL,
   maxNumberNonGroupBeamReporting [11] ENUMERATED { n1(0), n2(1), n4(2) }
       OPTIONAL,
   groupBeamReporting [12] ENUMERATED { supported(0) } OPTIONAL,
   uplinkBeamManagement [13] SEQUENCE {
      maxNumberSRS-ResourcePerSet-BM [0] ENUMERATED { n2(0), n4(1), n8(2), 
         n16(3) },
      maxNumberSRS-ResourceSet [1] INTEGER (1..8)
   } OPTIONAL,
   maxNumberCSI-RS-BFD [14] INTEGER (1..64) OPTIONAL,
   maxNumberSSB-BFD [15] INTEGER (1..64) OPTIONAL,
   maxNumberCSI-RS-SSB-CBD [16] INTEGER (1..256) OPTIONAL,
   dummy2 [17] ENUMERATED { supported(0) } OPTIONAL,
   twoPortsPTRS-UL [18] ENUMERATED { supported(0) } OPTIONAL,
   dummy5 [19] SRS-Resources OPTIONAL,
   dummy3 [20] INTEGER (1..4) OPTIONAL,
   beamReportTiming [21] SEQUENCE {
      scs-15kHz [0] ENUMERATED { sym2(0), sym4(1), sym8(2) } OPTIONAL,
      scs-30kHz [1] ENUMERATED { sym4(0), sym8(1), sym14(2), sym28(3) }
          OPTIONAL,
      scs-60kHz [2] ENUMERATED { sym8(0), sym14(1), sym28(2) } OPTIONAL,
      scs-120kHz [3] ENUMERATED { sym14(0), sym28(1), sym56(2) } OPTIONAL
   } OPTIONAL,
   ptrs-DensityRecommendationSetDL [22] SEQUENCE {
      scs-15kHz [0] PTRS-DensityRecommendationDL OPTIONAL,
      scs-30kHz [1] PTRS-DensityRecommendationDL OPTIONAL,
      scs-60kHz [2] PTRS-DensityRecommendationDL OPTIONAL,
      scs-120kHz [3] PTRS-DensityRecommendationDL OPTIONAL
   } OPTIONAL,
   ptrs-DensityRecommendationSetUL [23] SEQUENCE {
      scs-15kHz [0] PTRS-DensityRecommendationUL OPTIONAL,
      scs-30kHz [1] PTRS-DensityRecommendationUL OPTIONAL,
      scs-60kHz [2] PTRS-DensityRecommendationUL OPTIONAL,
      scs-120kHz [3] PTRS-DensityRecommendationUL OPTIONAL
   } OPTIONAL,
   dummy4 [24] DummyH OPTIONAL,
   aperiodicTRS [25] ENUMERATED { supported(0) } OPTIONAL,
   ...,
   [[
      dummy6 [26] ENUMERATED { true(0) } OPTIONAL,
      beamManagementSSB-CSI-RS [27] BeamManagementSSB-CSI-RS OPTIONAL,
      beamSwitchTiming [28] SEQUENCE {
         scs-60kHz [0] ENUMERATED { sym14(0), sym28(1), sym48(2), sym224(3), 
            sym336(4) } OPTIONAL,
         scs-120kHz [1] ENUMERATED { sym14(0), sym28(1), sym48(2), sym224(3), 
            sym336(4) } OPTIONAL
      } OPTIONAL,
      codebookParameters [29] CodebookParameters OPTIONAL,
      csi-RS-IM-ReceptionForFeedback [30] CSI-RS-IM-ReceptionForFeedback
          OPTIONAL,
      csi-RS-ProcFrameworkForSRS [31] CSI-RS-ProcFrameworkForSRS OPTIONAL,
      csi-ReportFramework [32] CSI-ReportFramework OPTIONAL,
      csi-RS-ForTracking [33] CSI-RS-ForTracking OPTIONAL,
      srs-AssocCSI-RS [34] SEQUENCE (SIZE (1..maxNrofCSI-RS-Resources)) OF SupportedCSI-RS-Resource
          OPTIONAL,
      spatialRelations [35] SpatialRelations OPTIONAL
   ]],
   [[
      defaultQCL-TwoTCI-r16 [36] ENUMERATED { supported(0) } OPTIONAL,
      codebookParametersPerBand-r16 [37] CodebookParameters-v1610 OPTIONAL,
      simul-SpatialRelationUpdatePUCCHResGroup-r16 [38] ENUMERATED { 
         supported(0) } OPTIONAL,
      maxNumberSCellBFR-r16 [39] ENUMERATED { n1(0), n2(1), n4(2), n8(3) }
          OPTIONAL,
      simultaneousReceptionDiffTypeD-r16 [40] ENUMERATED { supported(0) }
          OPTIONAL,
      ssb-csirs-SINR-measurement-r16 [41] SEQUENCE {
         maxNumberSSB-CSIRS-OneTx-CMR-r16 [0] ENUMERATED { n8(0), n16(1), 
            n32(2), n64(3) },
         maxNumberCSI-IM-NZP-IMR-res-r16 [1] ENUMERATED { n8(0), n16(1), n32(2)
            , n64(3) },
         maxNumberCSIRS-2Tx-res-r16 [2] ENUMERATED { n0(0), n4(1), n8(2), 
            n16(3), n32(4), n64(5) },
         maxNumberSSB-CSIRS-res-r16 [3] ENUMERATED { n8(0), n16(1), n32(2), 
            n64(3), n128(4) },
         maxNumberCSI-IM-NZP-IMR-res-mem-r16 [4] ENUMERATED { n8(0), n16(1), 
            n32(2), n64(3), n128(4) },
         supportedCSI-RS-Density-CMR-r16 [5] ENUMERATED { one(0), three(1), 
            oneAndThree(2) },
         maxNumberAperiodicCSI-RS-Res-r16 [6] ENUMERATED { n2(0), n4(1), n8(2)
            , n16(3), n32(4), n64(5) },
         supportedSINR-meas-r16 [7] ENUMERATED { ssbWithCSI-IM(0), 
            ssbWithNZP-IMR(1), csirsWithNZP-IMR(2), csi-RSWithoutIMR(3) }
             OPTIONAL
      } OPTIONAL,
      nonGroupSINR-reporting-r16 [42] ENUMERATED { n1(0), n2(1), n4(2) }
          OPTIONAL,
      groupSINR-reporting-r16 [43] ENUMERATED { supported(0) } OPTIONAL,
      multiDCI-multiTRP-Parameters-r16 [44] SEQUENCE {
       -- R1 16-2a-0: Overlapping PDSCHs in time and fully overlapping in frequency and time
         overlapPDSCHsFullyFreqTime-r16 [0] INTEGER (1..2) OPTIONAL,
       -- R1 16-2a-1: Overlapping PDSCHs in time and partially overlapping in frequency and time
         overlapPDSCHsInTimePartiallyFreq-r16 [1] ENUMERATED { supported(0) }
             OPTIONAL,
       -- R1 16-2a-2: Out of order operation for DL
         outOfOrderOperationDL-r16 [2] SEQUENCE {
            supportPDCCH-ToPDSCH-r16 [0] ENUMERATED { supported(0) } OPTIONAL,
            supportPDSCH-ToHARQ-ACK-r16 [1] ENUMERATED { supported(0) }
                OPTIONAL
         } OPTIONAL,
       -- R1 16-2a-3: Out of order operation for UL
         outOfOrderOperationUL-r16 [3] ENUMERATED { supported(0) } OPTIONAL,
       -- R1 16-2a-5: Separate CRS rate matching
         separateCRS-RateMatching-r16 [4] ENUMERATED { supported(0) } OPTIONAL,
       -- R1 16-2a-6: Default QCL enhancement for multi-DCI based multi-TRP
         defaultQCL-PerCORESETPoolIndex-r16 [5] ENUMERATED { supported(0) }
             OPTIONAL,
       -- R1 16-2a-7: Maximum number of activated TCI states
         maxNumberActivatedTCI-States-r16 [6] SEQUENCE {
            maxNumberPerCORESET-Pool-r16 [0] ENUMERATED { n1(0), n2(1), n4(2), 
               n8(3) },
            maxTotalNumberAcrossCORESET-Pool-r16 [1] ENUMERATED { n2(0), n4(1)
               , n8(2), n16(3) }
         } OPTIONAL
      } OPTIONAL,
      singleDCI-SDM-scheme-Parameters-r16 [45] SEQUENCE {
       -- R1 16-2b-1b: Single-DCI based SDM scheme - Support of new DMRS port entry
         supportNewDMRS-Port-r16 [0] ENUMERATED { supported1(0), supported2(1)
            , supported3(2) } OPTIONAL,
       -- R1 16-2b-1a: Support of s-port DL PTRS
         supportTwoPortDL-PTRS-r16 [1] ENUMERATED { supported(0) } OPTIONAL
      } OPTIONAL,
      supportFDM-SchemeA-r16 [46] ENUMERATED { supported(0) } OPTIONAL,
      supportCodeWordSoftCombining-r16 [47] ENUMERATED { supported(0) }
          OPTIONAL,
      supportTDM-SchemeA-r16 [48] ENUMERATED { kb3(0), kb5(1), kb10(2), kb20(3)
         , noRestriction(4) } OPTIONAL,
      supportInter-slotTDM-r16 [49] SEQUENCE {
         supportRepNumPDSCH-TDRA-r16 [0] ENUMERATED { n2(0), n3(1), n4(2), 
            n5(3), n6(4), n7(5), n8(6), n16(7) },
         maxTBS-Size-r16 [1] ENUMERATED { kb3(0), kb5(1), kb10(2), kb20(3), 
            noRestriction(4) },
         maxNumberTCI-states-r16 [2] INTEGER (1..2)
      } OPTIONAL,
      lowPAPR-DMRS-PDSCH-r16 [50] ENUMERATED { supported(0) } OPTIONAL,
      lowPAPR-DMRS-PUSCHwithoutPrecoding-r16 [51] ENUMERATED { supported(0) }
          OPTIONAL,
      lowPAPR-DMRS-PUCCH-r16 [52] ENUMERATED { supported(0) } OPTIONAL,
      lowPAPR-DMRS-PUSCHwithPrecoding-r16 [53] ENUMERATED { supported(0) }
          OPTIONAL,
      csi-ReportFrameworkExt-r16 [54] CSI-ReportFrameworkExt-r16 OPTIONAL,
      codebookParametersAddition-r16 [55] CodebookParametersAddition-r16
          OPTIONAL,
      codebookComboParametersAddition-r16 [56] 
         CodebookComboParametersAddition-r16 OPTIONAL,
      beamCorrespondenceSSB-based-r16 [57] ENUMERATED { supported(0) } OPTIONAL
         ,
      beamCorrespondenceCSI-RS-based-r16 [58] ENUMERATED { supported(0) }
          OPTIONAL,
      beamSwitchTiming-r16 [59] SEQUENCE {
         scs-60kHz-r16 [0] ENUMERATED { sym224(0), sym336(1) } OPTIONAL,
         scs-120kHz-r16 [1] ENUMERATED { sym224(0), sym336(1) } OPTIONAL
      } OPTIONAL
   ]],
   [[
      semi-PersistentL1-SINR-Report-PUCCH-r16 [60] SEQUENCE {
         supportReportFormat1-2OFDM-syms-r16 [0] ENUMERATED { supported(0) }
             OPTIONAL,
         supportReportFormat4-14OFDM-syms-r16 [1] ENUMERATED { supported(0) }
             OPTIONAL
      } OPTIONAL,
      semi-PersistentL1-SINR-Report-PUSCH-r16 [61] ENUMERATED { supported(0) }
          OPTIONAL
   ]],
   [[
      spatialRelations-v1640 [62] SEQUENCE {
         maxNumberConfiguredSpatialRelations-v1640 [0] ENUMERATED { n96(0), 
            n128(1), n160(2), n192(3), n224(4), n256(5), n288(6), n320(7) }
      } OPTIONAL,
      support64CandidateBeamRS-BFR-r16 [63] ENUMERATED { supported(0) }
          OPTIONAL
   ]],
   [[
      maxMIMO-LayersForMulti-DCI-mTRP-r16 [64] ENUMERATED { supported(0) }
          OPTIONAL
   ]],
   [[
      supportedSINR-meas-v1670 [65] BIT STRING  (SIZE (4)) OPTIONAL
   ]],
   [[
      srs-increasedRepetition-r17 [66] ENUMERATED { supported(0) } OPTIONAL,
      srs-partialFrequencySounding-r17 [67] ENUMERATED { supported(0) }
          OPTIONAL,
      srs-startRB-locationHoppingPartial-r17 [68] ENUMERATED { supported(0) }
          OPTIONAL,
      srs-combEight-r17 [69] ENUMERATED { supported(0) } OPTIONAL,
      codebookParametersfetype2-r17 [70] CodebookParametersfetype2-r17 OPTIONAL
         ,
      mTRP-PUSCH-twoCSI-RS-r17 [71] ENUMERATED { supported(0) } OPTIONAL,
      mTRP-PUCCH-InterSlot-r17 [72] ENUMERATED { pf0-2(0), pf1-3-4(1), pf0-4(2)
          } OPTIONAL,
      mTRP-PUCCH-CyclicMapping-r17 [73] ENUMERATED { supported(0) } OPTIONAL,
      mTRP-PUCCH-SecondTPC-r17 [74] ENUMERATED { supported(0) } OPTIONAL,
      mTRP-BFR-twoBFD-RS-Set-r17 [75] SEQUENCE {
         maxBFD-RS-resourcesPerSetPerBWP-r17 [0] ENUMERATED { n1(0), n2(1) },
         maxBFR-r17 [1] INTEGER (1..9),
         maxBFD-RS-resourcesAcrossSetsPerBWP-r17 [2] ENUMERATED { n2(0), n3(1)
            , n4(2) }
      } OPTIONAL,
      mTRP-BFR-PUCCH-SR-perCG-r17 [76] ENUMERATED { n1(0), n2(1) } OPTIONAL,
      mTRP-BFR-association-PUCCH-SR-r17 [77] ENUMERATED { supported(0) }
          OPTIONAL,
      sfn-SimulTwoTCI-AcrossMultiCC-r17 [78] ENUMERATED { supported(0) }
          OPTIONAL,
      sfn-DefaultDL-BeamSetup-r17 [79] ENUMERATED { supported(0) } OPTIONAL,
      sfn-DefaultUL-BeamSetup-r17 [80] ENUMERATED { supported(0) } OPTIONAL,
      srs-TriggeringOffset-r17 [81] ENUMERATED { n1(0), n2(1), n4(2) } OPTIONAL
         ,
      srs-TriggeringDCI-r17 [82] ENUMERATED { supported(0) } OPTIONAL,
      codebookComboParameterMixedType-r17 [83] 
         CodebookComboParameterMixedType-r17 OPTIONAL,
      unifiedJointTCI-r17 [84] SEQUENCE {
         maxConfiguredJointTCI-r17 [0] ENUMERATED { n8(0), n12(1), n16(2), 
            n24(3), n32(4), n48(5), n64(6), n128(7) },
         maxActivatedTCIAcrossCC-r17 [1] ENUMERATED { n1(0), n2(1), n4(2), 
            n8(3), n16(4) }
      } OPTIONAL,
      unifiedJointTCI-multiMAC-CE-r17 [85] SEQUENCE {
         minBeamApplicationTime-r17 [0] ENUMERATED { n1(0), n2(1), n4(2), n7(3)
            , n14(4), n28(5), n42(6), n56(7), n70(8), n84(9), n98(10), n112(11)
            , n224(12), n336(13) } OPTIONAL,
         maxNumMAC-CE-PerCC [1] ENUMERATED { n2(0), n3(1), n4(2), n5(3), n6(4)
            , n7(5), n8(6) }
      } OPTIONAL,
      unifiedJointTCI-perBWP-CA-r17 [86] ENUMERATED { supported(0) } OPTIONAL,
      unifiedJointTCI-ListSharingCA-r17 [87] ENUMERATED { n1(0), n2(1), n4(2), 
         n8(3) } OPTIONAL,
      unifiedJointTCI-commonMultiCC-r17 [88] ENUMERATED { supported(0) }
          OPTIONAL,
      unifiedJointTCI-BeamAlignDLRS-r17 [89] ENUMERATED { supported(0) }
          OPTIONAL,
      unifiedJointTCI-PC-association-r17 [90] ENUMERATED { supported(0) }
          OPTIONAL,
      unifiedJointTCI-Legacy-r17 [91] ENUMERATED { supported(0) } OPTIONAL,
      unifiedJointTCI-Legacy-SRS-r17 [92] ENUMERATED { supported(0) } OPTIONAL
         ,
      unifiedJointTCI-Legacy-CORESET0-r17 [93] ENUMERATED { supported(0) }
          OPTIONAL,
      unifiedJointTCI-SCellBFR-r17 [94] ENUMERATED { supported(0) } OPTIONAL,
      unifiedJointTCI-InterCell-r17 [95] SEQUENCE {
         additionalMAC-CE-PerCC-r17 [0] ENUMERATED { n0(0), n1(1), n2(2), n4(3)
             },
         additionalMAC-CE-AcrossCC-r17 [1] ENUMERATED { n0(0), n1(1), n2(2), 
            n4(3) }
      } OPTIONAL,
      unifiedSeparateTCI-r17 [96] SEQUENCE {
         maxConfiguredDL-TCI-r17 [0] ENUMERATED { n4(0), n8(1), n12(2), n16(3)
            , n24(4), n32(5), n48(6), n64(7), n128(8) },
         maxConfiguredUL-TCI-r17 [1] ENUMERATED { n4(0), n8(1), n12(2), n16(3)
            , n24(4), n32(5), n48(6), n64(7) },
         maxActivatedDL-TCIAcrossCC-r17 [2] ENUMERATED { n1(0), n2(1), n4(2), 
            n8(3), n16(4) },
         maxActivatedUL-TCIAcrossCC-r17 [3] ENUMERATED { n1(0), n2(1), n4(2), 
            n8(3), n16(4) }
      } OPTIONAL,
      unifiedSeparateTCI-multiMAC-CE-r17 [97] SEQUENCE {
         minBeamApplicationTime-r17 [0] ENUMERATED { n1(0), n2(1), n4(2), n7(3)
            , n14(4), n28(5), n42(6), n56(7), n70(8), n84(9), n98(10), n112(11)
            , n224(12), n336(13) },
         maxActivatedDL-TCIPerCC-r17 [1] INTEGER (2..8),
         maxActivatedUL-TCIPerCC-r17 [2] INTEGER (2..8)
      } OPTIONAL,
      unifiedSeparateTCI-perBWP-CA-r17 [98] ENUMERATED { supported(0) }
          OPTIONAL,
      unifiedSeparateTCI-ListSharingCA-r17 [99] SEQUENCE {
         maxNumListDL-TCI-r17 [0] ENUMERATED { n1(0), n2(1), n4(2), n8(3) }
             OPTIONAL,
         maxNumListUL-TCI-r17 [1] ENUMERATED { n1(0), n2(1), n4(2), n8(3) }
             OPTIONAL
      } OPTIONAL,
      unifiedSeparateTCI-commonMultiCC-r17 [100] ENUMERATED { supported(0) }
          OPTIONAL,
      unifiedSeparateTCI-InterCell-r17 [101] SEQUENCE {
         k-DL-PerCC-r17 [0] ENUMERATED { n0(0), n1(1), n2(2), n4(3) },
         k-UL-PerCC-r17 [1] ENUMERATED { n0(0), n1(1), n2(2), n4(3) },
         k-DL-AcrossCC-r17 [2] ENUMERATED { n0(0), n1(1), n2(2), n4(3) },
         k-UL-AcrossCC-r17 [3] ENUMERATED { n0(0), n1(1), n2(2), n4(3) }
      } OPTIONAL,
      unifiedJointTCI-mTRP-InterCell-BM-r17 [102] SEQUENCE {
         maxNumAdditionalPCI-L1-RSRP-r17 [0] INTEGER (1..7),
         maxNumSSB-ResourceL1-RSRP-AcrossCC-r17 [1] ENUMERATED { n1(0), n2(1), 
            n4(2), n8(3) }
      } OPTIONAL,
      mpe-Mitigation-r17 [103] SEQUENCE {
         maxNumP-MPR-RI-pairs-r17 [0] INTEGER (1..4),
         maxNumConfRS-r17 [1] ENUMERATED { n1(0), n2(1), n4(2), n8(3), n12(4), 
            n16(5), n28(6), n32(7), n48(8), n64(9) }
      } OPTIONAL,
      srs-PortReport-r17 [104] SEQUENCE {
         capVal1-r17 [0] ENUMERATED { n1(0), n2(1), n4(2) } OPTIONAL,
         capVal2-r17 [1] ENUMERATED { n1(0), n2(1), n4(2) } OPTIONAL,
         capVal3-r17 [2] ENUMERATED { n1(0), n2(1), n4(2) } OPTIONAL,
         capVal4-r17 [3] ENUMERATED { n1(0), n2(1), n4(2) } OPTIONAL
      } OPTIONAL,
      mTRP-PDCCH-individual-r17 [105] ENUMERATED { supported(0) } OPTIONAL,
      mTRP-PDCCH-anySpan-3Symbols-r17 [106] ENUMERATED { supported(0) }
          OPTIONAL,
      mTRP-PDCCH-TwoQCL-TypeD-r17 [107] ENUMERATED { supported(0) } OPTIONAL,
      mTRP-PUSCH-CSI-RS-r17 [108] SEQUENCE {
         maxNumPeriodicSRS-r17 [0] INTEGER (1..8),
         maxNumAperiodicSRS-r17 [1] INTEGER (1..8),
         maxNumSP-SRS-r17 [2] INTEGER (0..8),
         numSRS-ResourcePerCC-r17 [3] INTEGER (1..16),
         numSRS-ResourceNonCodebook-r17 [4] INTEGER (1..2)
      } OPTIONAL,
      mTRP-PUSCH-cyclicMapping-r17 [109] ENUMERATED { typeA(0), typeB(1), 
         both(2) } OPTIONAL,
      mTRP-PUSCH-secondTPC-r17 [110] ENUMERATED { supported(0) } OPTIONAL,
      mTRP-PUSCH-twoPHR-Reporting-r17 [111] ENUMERATED { supported(0) }
          OPTIONAL,
      mTRP-PUSCH-A-CSI-r17 [112] ENUMERATED { supported(0) } OPTIONAL,
      mTRP-PUSCH-SP-CSI-r17 [113] ENUMERATED { supported(0) } OPTIONAL,
      mTRP-PUSCH-CG-r17 [114] ENUMERATED { supported(0) } OPTIONAL,
      mTRP-PUCCH-MAC-CE-r17 [115] ENUMERATED { supported(0) } OPTIONAL,
      mTRP-PUCCH-maxNum-PC-FR1-r17 [116] INTEGER (3..8) OPTIONAL,
      mTRP-inter-Cell-r17 [117] SEQUENCE {
         maxNumAdditionalPCI-Case1-r17 [0] INTEGER (1..7),
         maxNumAdditionalPCI-Case2-r17 [1] INTEGER (0..7)
      } OPTIONAL,
      mTRP-GroupBasedL1-RSRP-r17 [118] SEQUENCE {
         maxNumBeamGroups-r17 [0] INTEGER (1..4),
         maxNumRS-WithinSlot-r17 [1] ENUMERATED { n2(0), n3(1), n4(2), n8(3), 
            n16(4), n32(5), n64(6) },
         maxNumRS-AcrossSlot-r17 [2] ENUMERATED { n8(0), n16(1), n32(2), n64(3)
            , n128(4) }
      } OPTIONAL,
      mTRP-BFD-RS-MAC-CE-r17 [119] ENUMERATED { n4(0), n8(1), n12(2), n16(3), 
         n32(4), n48(5), n64(6) } OPTIONAL,
      mTRP-CSI-EnhancementPerBand-r17 [120] SEQUENCE {
         maxNumNZP-CSI-RS-r17 [0] INTEGER (2..8),
         cSI-Report-mode-r17 [1] ENUMERATED { mode1(0), mode2(1), both(2) },
         supportedComboAcrossCCs-r17 [2] SEQUENCE (SIZE (1..16)) OF 
            CSI-MultiTRP-SupportedCombinations-r17,
         codebookModeNCJT-r17 [3] ENUMERATED { mode1(0), mode1And2(1) }
      } OPTIONAL,
      codebookComboParameterMultiTRP-r17 [121] 
         CodebookComboParameterMultiTRP-r17 OPTIONAL,
      mTRP-CSI-additionalCSI-r17 [122] ENUMERATED { x1(0), x2(1) } OPTIONAL,
      mTRP-CSI-N-Max2-r17 [123] ENUMERATED { supported(0) } OPTIONAL,
      mTRP-CSI-CMR-r17 [124] ENUMERATED { supported(0) } OPTIONAL,
      srs-partialFreqSounding-r17 [125] ENUMERATED { supported(0) } OPTIONAL,
      beamSwitchTiming-v1710 [126] SEQUENCE {
         scs-480kHz [0] ENUMERATED { sym56(0), sym112(1), sym192(2), sym896(3)
            , sym1344(4) } OPTIONAL,
         scs-960kHz [1] ENUMERATED { sym112(0), sym224(1), sym384(2), 
            sym1792(3), sym2688(4) } OPTIONAL
      } OPTIONAL,
      beamSwitchTiming-r17 [127] SEQUENCE {
         scs-480kHz-r17 [0] ENUMERATED { sym896(0), sym1344(1) } OPTIONAL,
         scs-960kHz-r17 [1] ENUMERATED { sym1792(0), sym2688(1) } OPTIONAL
      } OPTIONAL,
      beamReportTiming-v1710 [128] SEQUENCE {
         scs-480kHz-r17 [0] ENUMERATED { sym56(0), sym112(1), sym224(2) }
             OPTIONAL,
         scs-960kHz-r17 [1] ENUMERATED { sym112(0), sym224(1), sym448(2) }
             OPTIONAL
      } OPTIONAL,
      maxNumberRxTxBeamSwitchDL-v1710 [129] SEQUENCE {
         scs-480kHz-r17 [0] ENUMERATED { n2(0), n4(1), n7(2) } OPTIONAL,
         scs-960kHz-r17 [1] ENUMERATED { n1(0), n2(1), n4(2), n7(3) } OPTIONAL
      } OPTIONAL
   ]],
   [[
      srs-PortReportSP-AP-r17 [130] ENUMERATED { supported(0) } OPTIONAL,
      maxNumberRxBeam-v1720 [131] INTEGER (9..12) OPTIONAL,
      sfn-ImplicitRS-twoTCI-r17 [132] ENUMERATED { supported(0) } OPTIONAL,
      sfn-QCL-TypeD-Collision-twoTCI-r17 [133] ENUMERATED { supported(0) }
          OPTIONAL,
      mTRP-CSI-numCPU-r17 [134] ENUMERATED { n2(0), n3(1), n4(2) } OPTIONAL
   ]],
   [[
      supportRepNumPDSCH-TDRA-DCI-1-2-r17 [135] ENUMERATED { n2(0), n3(1), 
         n4(2), n5(3), n6(4), n7(5), n8(6), n16(7) } OPTIONAL
   ]]
}

GeneralParametersMRDC-XDD-Diff ::= SEQUENCE {
   splitSRB-WithOneUL-Path [0] ENUMERATED { supported(0) } OPTIONAL,
   splitDRB-withUL-Both-MCG-SCG [1] ENUMERATED { supported(0) } OPTIONAL,
   srb3 [2] ENUMERATED { supported(0) } OPTIONAL,
   dummy [3] ENUMERATED { supported(0) } OPTIONAL,
   ...
}

UE-MRDC-CapabilityAddXDD-Mode ::= SEQUENCE {
   measAndMobParametersMRDC-XDD-Diff [0] MeasAndMobParametersMRDC-XDD-Diff
       OPTIONAL,
   generalParametersMRDC-XDD-Diff [1] GeneralParametersMRDC-XDD-Diff OPTIONAL
}

UE-MRDC-CapabilityAddFRX-Mode ::= SEQUENCE {
   measAndMobParametersMRDC-FRX-Diff [0] MeasAndMobParametersMRDC-FRX-Diff
}

-- TAG-MRDC-PARAMETERS-STOP
-- TAG-NRDC-PARAMETERS-START
NRDC-Parameters ::= SEQUENCE {
   measAndMobParametersNRDC [0] MeasAndMobParametersMRDC OPTIONAL,
   generalParametersNRDC [1] GeneralParametersMRDC-XDD-Diff OPTIONAL,
   fdd-Add-UE-NRDC-Capabilities [2] UE-MRDC-CapabilityAddXDD-Mode OPTIONAL,
   tdd-Add-UE-NRDC-Capabilities [3] UE-MRDC-CapabilityAddXDD-Mode OPTIONAL,
   fr1-Add-UE-NRDC-Capabilities [4] UE-MRDC-CapabilityAddFRX-Mode OPTIONAL,
   fr2-Add-UE-NRDC-Capabilities [5] UE-MRDC-CapabilityAddFRX-Mode OPTIONAL,
   dummy2 [6] OCTET STRING OPTIONAL,
   dummy [7] SEQUENCE {

   } OPTIONAL
}

NRDC-Parameters-v1570 ::= SEQUENCE {
   sfn-SyncNRDC [0] ENUMERATED { supported(0) } OPTIONAL
}

NRDC-Parameters-v15c0 ::= SEQUENCE {
   pdcp-DuplicationSplitSRB [0] ENUMERATED { supported(0) } OPTIONAL,
   pdcp-DuplicationSplitDRB [1] ENUMERATED { supported(0) } OPTIONAL
}

NRDC-Parameters-v1610 ::= SEQUENCE {
   measAndMobParametersNRDC-v1610 [0] MeasAndMobParametersMRDC-v1610 OPTIONAL
}

NRDC-Parameters-v1700 ::= SEQUENCE {
   f1c-OverNR-RRC-r17 [0] ENUMERATED { supported(0) } OPTIONAL,
   measAndMobParametersNRDC-v1700 [1] MeasAndMobParametersMRDC-v1700
}

Phy-ParametersCommon ::= SEQUENCE {
   csi-RS-CFRA-ForHO [0] ENUMERATED { supported(0) } OPTIONAL,
   dynamicPRB-BundlingDL [1] ENUMERATED { supported(0) } OPTIONAL,
   sp-CSI-ReportPUCCH [2] ENUMERATED { supported(0) } OPTIONAL,
   sp-CSI-ReportPUSCH [3] ENUMERATED { supported(0) } OPTIONAL,
   nzp-CSI-RS-IntefMgmt [4] ENUMERATED { supported(0) } OPTIONAL,
   type2-SP-CSI-Feedback-LongPUCCH [5] ENUMERATED { supported(0) } OPTIONAL,
   precoderGranularityCORESET [6] ENUMERATED { supported(0) } OPTIONAL,
   dynamicHARQ-ACK-Codebook [7] ENUMERATED { supported(0) } OPTIONAL,
   semiStaticHARQ-ACK-Codebook [8] ENUMERATED { supported(0) } OPTIONAL,
   spatialBundlingHARQ-ACK [9] ENUMERATED { supported(0) } OPTIONAL,
   dynamicBetaOffsetInd-HARQ-ACK-CSI [10] ENUMERATED { supported(0) } OPTIONAL,
   pucch-Repetition-F1-3-4 [11] ENUMERATED { supported(0) } OPTIONAL,
   ra-Type0-PUSCH [12] ENUMERATED { supported(0) } OPTIONAL,
   dynamicSwitchRA-Type0-1-PDSCH [13] ENUMERATED { supported(0) } OPTIONAL,
   dynamicSwitchRA-Type0-1-PUSCH [14] ENUMERATED { supported(0) } OPTIONAL,
   pdsch-MappingTypeA [15] ENUMERATED { supported(0) } OPTIONAL,
   pdsch-MappingTypeB [16] ENUMERATED { supported(0) } OPTIONAL,
   interleavingVRB-ToPRB-PDSCH [17] ENUMERATED { supported(0) } OPTIONAL,
   interSlotFreqHopping-PUSCH [18] ENUMERATED { supported(0) } OPTIONAL,
   type1-PUSCH-RepetitionMultiSlots [19] ENUMERATED { supported(0) } OPTIONAL,
   type2-PUSCH-RepetitionMultiSlots [20] ENUMERATED { supported(0) } OPTIONAL,
   pusch-RepetitionMultiSlots [21] ENUMERATED { supported(0) } OPTIONAL,
   pdsch-RepetitionMultiSlots [22] ENUMERATED { supported(0) } OPTIONAL,
   downlinkSPS [23] ENUMERATED { supported(0) } OPTIONAL,
   configuredUL-GrantType1 [24] ENUMERATED { supported(0) } OPTIONAL,
   configuredUL-GrantType2 [25] ENUMERATED { supported(0) } OPTIONAL,
   pre-EmptIndication-DL [26] ENUMERATED { supported(0) } OPTIONAL,
   cbg-TransIndication-DL [27] ENUMERATED { supported(0) } OPTIONAL,
   cbg-TransIndication-UL [28] ENUMERATED { supported(0) } OPTIONAL,
   cbg-FlushIndication-DL [29] ENUMERATED { supported(0) } OPTIONAL,
   dynamicHARQ-ACK-CodeB-CBG-Retx-DL [30] ENUMERATED { supported(0) } OPTIONAL,
   rateMatchingResrcSetSemi-Static [31] ENUMERATED { supported(0) } OPTIONAL,
   rateMatchingResrcSetDynamic [32] ENUMERATED { supported(0) } OPTIONAL,
   bwp-SwitchingDelay [33] ENUMERATED { type1(0), type2(1) } OPTIONAL,
   ...,
   [[
      dummy [34] ENUMERATED { supported(0) } OPTIONAL
   ]],
   [[
      maxNumberSearchSpaces [35] ENUMERATED { n10(0) } OPTIONAL,
      rateMatchingCtrlResrcSetDynamic [36] ENUMERATED { supported(0) } OPTIONAL
         ,
      maxLayersMIMO-Indication [37] ENUMERATED { supported(0) } OPTIONAL
   ]],
   [[
      spCellPlacement [38] CarrierAggregationVariant OPTIONAL
   ]],
   [[
      twoStepRACH-r16 [39] ENUMERATED { supported(0) } OPTIONAL,
      dci-Format1-2And0-2-r16 [40] ENUMERATED { supported(0) } OPTIONAL,
      monitoringDCI-SameSearchSpace-r16 [41] ENUMERATED { supported(0) }
          OPTIONAL,
      type2-CG-ReleaseDCI-0-1-r16 [42] ENUMERATED { supported(0) } OPTIONAL,
      type2-CG-ReleaseDCI-0-2-r16 [43] ENUMERATED { supported(0) } OPTIONAL,
      sps-ReleaseDCI-1-1-r16 [44] ENUMERATED { supported(0) } OPTIONAL,
      sps-ReleaseDCI-1-2-r16 [45] ENUMERATED { supported(0) } OPTIONAL,
      csi-TriggerStateNon-ActiveBWP-r16 [46] ENUMERATED { supported(0) }
          OPTIONAL,
      separateSMTC-InterIAB-Support-r16 [47] ENUMERATED { supported(0) }
          OPTIONAL,
      separateRACH-IAB-Support-r16 [48] ENUMERATED { supported(0) } OPTIONAL,
      ul-flexibleDL-SlotFormatSemiStatic-IAB-r16 [49] ENUMERATED { supported(0)
          } OPTIONAL,
      ul-flexibleDL-SlotFormatDynamics-IAB-r16 [50] ENUMERATED { supported(0) }
          OPTIONAL,
      dft-S-OFDM-WaveformUL-IAB-r16 [51] ENUMERATED { supported(0) } OPTIONAL,
      dci-25-AI-RNTI-Support-IAB-r16 [52] ENUMERATED { supported(0) } OPTIONAL
         ,
      t-DeltaReceptionSupport-IAB-r16 [53] ENUMERATED { supported(0) } OPTIONAL
         ,
      guardSymbolReportReception-IAB-r16 [54] ENUMERATED { supported(0) }
          OPTIONAL,
      harqACK-CB-SpatialBundlingPUCCH-Group-r16 [55] ENUMERATED { supported(0)
          } OPTIONAL,
      crossSlotScheduling-r16 [56] SEQUENCE {
         non-SharedSpectrumChAccess-r16 [0] ENUMERATED { supported(0) }
             OPTIONAL,
         sharedSpectrumChAccess-r16 [1] ENUMERATED { supported(0) } OPTIONAL
      } OPTIONAL,
      maxNumberSRS-PosPathLossEstimateAllServingCells-r16 [57] ENUMERATED { 
         n1(0), n4(1), n8(2), n16(3) } OPTIONAL,
      extendedCG-Periodicities-r16 [58] ENUMERATED { supported(0) } OPTIONAL,
      extendedSPS-Periodicities-r16 [59] ENUMERATED { supported(0) } OPTIONAL,
      codebookVariantsList-r16 [60] CodebookVariantsList-r16 OPTIONAL,
      pusch-RepetitionTypeA-r16 [61] SEQUENCE {
         sharedSpectrumChAccess-r16 [0] ENUMERATED { supported(0) } OPTIONAL,
         non-SharedSpectrumChAccess-r16 [1] ENUMERATED { supported(0) }
             OPTIONAL
      } OPTIONAL,
      dci-DL-PriorityIndicator-r16 [62] ENUMERATED { supported(0) } OPTIONAL,
      dci-UL-PriorityIndicator-r16 [63] ENUMERATED { supported(0) } OPTIONAL,
      maxNumberPathlossRS-Update-r16 [64] ENUMERATED { n4(0), n8(1), n16(2), 
         n32(3), n64(4) } OPTIONAL,
      type2-HARQ-ACK-Codebook-r16 [65] ENUMERATED { supported(0) } OPTIONAL,
      maxTotalResourcesForAcrossFreqRanges-r16 [66] SEQUENCE {
         maxNumberResWithinSlotAcrossCC-AcrossFR-r16 [0] ENUMERATED { n2(0), 
            n4(1), n8(2), n12(3), n16(4), n32(5), n64(6), n128(7) } OPTIONAL,
         maxNumberResAcrossCC-AcrossFR-r16 [1] ENUMERATED { n2(0), n4(1), n8(2)
            , n12(3), n16(4), n32(5), n40(6), n48(7), n64(8), n72(9), n80(10), 
            n96(11), n128(12), n256(13) } OPTIONAL
      } OPTIONAL,
      harqACK-separateMultiDCI-MultiTRP-r16 [67] SEQUENCE {
         maxNumberLongPUCCHs-r16 [0] ENUMERATED { longAndLong(0), 
            longAndShort(1), shortAndShort(2) } OPTIONAL
      } OPTIONAL,
      harqACK-jointMultiDCI-MultiTRP-r16 [68] ENUMERATED { supported(0) }
          OPTIONAL,
      bwp-SwitchingMultiCCs-r16 [69] EXPLICIT CHOICE {
         type1-r16 [0] ENUMERATED { us100(0), us200(1) },
         type2-r16 [1] ENUMERATED { us200(0), us400(1), us800(2), us1000(3) }
      } OPTIONAL
   ]],
   [[
      targetSMTC-SCG-r16 [70] ENUMERATED { supported(0) } OPTIONAL,
      supportRepetitionZeroOffsetRV-r16 [71] ENUMERATED { supported(0) }
          OPTIONAL,
      cbg-TransInOrderPUSCH-UL-r16 [72] ENUMERATED { supported(0) } OPTIONAL
   ]],
   [[
      bwp-SwitchingMultiDormancyCCs-r16 [73] EXPLICIT CHOICE {
         type1-r16 [0] ENUMERATED { us100(0), us200(1) },
         type2-r16 [1] ENUMERATED { us200(0), us400(1), us800(2), us1000(3) }
      } OPTIONAL,
      supportRetx-Diff-CoresetPool-Multi-DCI-TRP-r16 [74] ENUMERATED { 
         notSupported(0) } OPTIONAL,
      pdcch-MonitoringAnyOccasionsWithSpanGapCrossCarrierSch-r16 [75] 
         ENUMERATED { mode2(0), mode3(1) } OPTIONAL
   ]],
   [[
      newBeamIdentifications2PortCSI-RS-r16 [76] ENUMERATED { supported(0) }
          OPTIONAL,
      pathlossEstimation2PortCSI-RS-r16 [77] ENUMERATED { supported(0) }
          OPTIONAL
   ]],
   [[
      mux-HARQ-ACK-withoutPUCCH-onPUSCH-r16 [78] ENUMERATED { supported(0) }
          OPTIONAL
   ]],
   [[
      guardSymbolReportReception-IAB-r17 [79] ENUMERATED { supported(0) }
          OPTIONAL,
      restricted-IAB-DU-BeamReception-r17 [80] ENUMERATED { supported(0) }
          OPTIONAL,
      recommended-IAB-MT-BeamTransmission-r17 [81] ENUMERATED { supported(0) }
          OPTIONAL,
      case6-TimingAlignmentReception-IAB-r17 [82] ENUMERATED { supported(0) }
          OPTIONAL,
      case7-TimingAlignmentReception-IAB-r17 [83] ENUMERATED { supported(0) }
          OPTIONAL,
      dl-tx-PowerAdjustment-IAB-r17 [84] ENUMERATED { supported(0) } OPTIONAL,
      desired-ul-tx-PowerAdjustment-r17 [85] ENUMERATED { supported(0) }
          OPTIONAL,
      fdm-SoftResourceAvailability-DynamicIndication-r17 [86] ENUMERATED { 
         supported(0) } OPTIONAL,
      updated-T-DeltaRangeReception-r17 [87] ENUMERATED { supported(0) }
          OPTIONAL,
      slotBasedDynamicPUCCH-Rep-r17 [88] ENUMERATED { supported(0) } OPTIONAL,
      sps-HARQ-ACK-Deferral-r17 [89] SEQUENCE {
         non-SharedSpectrumChAccess-r17 [0] ENUMERATED { supported(0) }
             OPTIONAL,
         sharedSpectrumChAccess-r17 [1] ENUMERATED { supported(0) } OPTIONAL
      } OPTIONAL,
      unifiedJointTCI-commonUpdate-r17 [90] INTEGER (1..4) OPTIONAL,
      mTRP-PDCCH-singleSpan-r17 [91] ENUMERATED { supported(0) } OPTIONAL,
      supportedActivatedPRS-ProcessingWindow-r17 [92] ENUMERATED { n2(0), n3(1)
         , n4(2) } OPTIONAL,
      cg-TimeDomainAllocationExtension-r17 [93] ENUMERATED { supported(0) }
          OPTIONAL
   ]],
   [[
      ta-BasedPDC-TN-NonSharedSpectrumChAccess-r17 [94] ENUMERATED { 
         supported(0) } OPTIONAL,
      directionalCollisionDC-IAB-r17 [95] ENUMERATED { supported(0) } OPTIONAL
   ]],
   [[
      dummy1 [96] ENUMERATED { supported(0) } OPTIONAL,
      dummy2 [97] ENUMERATED { supported(0) } OPTIONAL,
      dummy3 [98] ENUMERATED { supported(0) } OPTIONAL,
      dummy4 [99] ENUMERATED { supported(0) } OPTIONAL,
      srs-AdditionalRepetition-r17 [100] ENUMERATED { supported(0) } OPTIONAL,
      pusch-Repetition-CG-SDT-r17 [101] ENUMERATED { supported(0) } OPTIONAL
   ]],
   [[
      multiPDSCH-PerSlotType1-CB-Support-r17 [102] ENUMERATED { supported(0) }
          OPTIONAL
   ]]
}

Phy-ParametersXDD-Diff ::= SEQUENCE {
   dynamicSFI [0] ENUMERATED { supported(0) } OPTIONAL,
   twoPUCCH-F0-2-ConsecSymbols [1] ENUMERATED { supported(0) } OPTIONAL,
   twoDifferentTPC-Loop-PUSCH [2] ENUMERATED { supported(0) } OPTIONAL,
   twoDifferentTPC-Loop-PUCCH [3] ENUMERATED { supported(0) } OPTIONAL,
   ...,
   [[
      dl-SchedulingOffset-PDSCH-TypeA [4] ENUMERATED { supported(0) } OPTIONAL
         ,
      dl-SchedulingOffset-PDSCH-TypeB [5] ENUMERATED { supported(0) } OPTIONAL
         ,
      ul-SchedulingOffset [6] ENUMERATED { supported(0) } OPTIONAL
   ]]
}

Phy-ParametersFRX-Diff ::= SEQUENCE {
   dynamicSFI [0] ENUMERATED { supported(0) } OPTIONAL,
   dummy1 [1] BIT STRING  (SIZE (2)) OPTIONAL,
   twoFL-DMRS [2] BIT STRING  (SIZE (2)) OPTIONAL,
   dummy2 [3] BIT STRING  (SIZE (2)) OPTIONAL,
   dummy3 [4] BIT STRING  (SIZE (2)) OPTIONAL,
   supportedDMRS-TypeDL [5] ENUMERATED { type1(0), type1And2(1) } OPTIONAL,
   supportedDMRS-TypeUL [6] ENUMERATED { type1(0), type1And2(1) } OPTIONAL,
   semiOpenLoopCSI [7] ENUMERATED { supported(0) } OPTIONAL,
   csi-ReportWithoutPMI [8] ENUMERATED { supported(0) } OPTIONAL,
   csi-ReportWithoutCQI [9] ENUMERATED { supported(0) } OPTIONAL,
   onePortsPTRS [10] BIT STRING  (SIZE (2)) OPTIONAL,
   twoPUCCH-F0-2-ConsecSymbols [11] ENUMERATED { supported(0) } OPTIONAL,
   pucch-F2-WithFH [12] ENUMERATED { supported(0) } OPTIONAL,
   pucch-F3-WithFH [13] ENUMERATED { supported(0) } OPTIONAL,
   pucch-F4-WithFH [14] ENUMERATED { supported(0) } OPTIONAL,
   pucch-F0-2WithoutFH [15] ENUMERATED { notSupported(0) } OPTIONAL,
   pucch-F1-3-4WithoutFH [16] ENUMERATED { notSupported(0) } OPTIONAL,
   mux-SR-HARQ-ACK-CSI-PUCCH-MultiPerSlot [17] ENUMERATED { supported(0) }
       OPTIONAL,
   uci-CodeBlockSegmentation [18] ENUMERATED { supported(0) } OPTIONAL,
   onePUCCH-LongAndShortFormat [19] ENUMERATED { supported(0) } OPTIONAL,
   twoPUCCH-AnyOthersInSlot [20] ENUMERATED { supported(0) } OPTIONAL,
   intraSlotFreqHopping-PUSCH [21] ENUMERATED { supported(0) } OPTIONAL,
   pusch-LBRM [22] ENUMERATED { supported(0) } OPTIONAL,
   pdcch-BlindDetectionCA [23] INTEGER (4..16) OPTIONAL,
   tpc-PUSCH-RNTI [24] ENUMERATED { supported(0) } OPTIONAL,
   tpc-PUCCH-RNTI [25] ENUMERATED { supported(0) } OPTIONAL,
   tpc-SRS-RNTI [26] ENUMERATED { supported(0) } OPTIONAL,
   absoluteTPC-Command [27] ENUMERATED { supported(0) } OPTIONAL,
   twoDifferentTPC-Loop-PUSCH [28] ENUMERATED { supported(0) } OPTIONAL,
   twoDifferentTPC-Loop-PUCCH [29] ENUMERATED { supported(0) } OPTIONAL,
   pusch-HalfPi-BPSK [30] ENUMERATED { supported(0) } OPTIONAL,
   pucch-F3-4-HalfPi-BPSK [31] ENUMERATED { supported(0) } OPTIONAL,
   almostContiguousCP-OFDM-UL [32] ENUMERATED { supported(0) } OPTIONAL,
   sp-CSI-RS [33] ENUMERATED { supported(0) } OPTIONAL,
   sp-CSI-IM [34] ENUMERATED { supported(0) } OPTIONAL,
   tdd-MultiDL-UL-SwitchPerSlot [35] ENUMERATED { supported(0) } OPTIONAL,
   multipleCORESET [36] ENUMERATED { supported(0) } OPTIONAL,
   ...,
   [[
      csi-RS-IM-ReceptionForFeedback [37] CSI-RS-IM-ReceptionForFeedback
          OPTIONAL,
      csi-RS-ProcFrameworkForSRS [38] CSI-RS-ProcFrameworkForSRS OPTIONAL,
      csi-ReportFramework [39] CSI-ReportFramework OPTIONAL,
      mux-SR-HARQ-ACK-CSI-PUCCH-OncePerSlot [40] SEQUENCE {
         sameSymbol [0] ENUMERATED { supported(0) } OPTIONAL,
         diffSymbol [1] ENUMERATED { supported(0) } OPTIONAL
      } OPTIONAL,
      mux-SR-HARQ-ACK-PUCCH [41] ENUMERATED { supported(0) } OPTIONAL,
      mux-MultipleGroupCtrlCH-Overlap [42] ENUMERATED { supported(0) } OPTIONAL
         ,
      dl-SchedulingOffset-PDSCH-TypeA [43] ENUMERATED { supported(0) } OPTIONAL
         ,
      dl-SchedulingOffset-PDSCH-TypeB [44] ENUMERATED { supported(0) } OPTIONAL
         ,
      ul-SchedulingOffset [45] ENUMERATED { supported(0) } OPTIONAL,
      dl-64QAM-MCS-TableAlt [46] ENUMERATED { supported(0) } OPTIONAL,
      ul-64QAM-MCS-TableAlt [47] ENUMERATED { supported(0) } OPTIONAL,
      cqi-TableAlt [48] ENUMERATED { supported(0) } OPTIONAL,
      oneFL-DMRS-TwoAdditionalDMRS-UL [49] ENUMERATED { supported(0) } OPTIONAL
         ,
      twoFL-DMRS-TwoAdditionalDMRS-UL [50] ENUMERATED { supported(0) } OPTIONAL
         ,
      oneFL-DMRS-ThreeAdditionalDMRS-UL [51] ENUMERATED { supported(0) }
          OPTIONAL
   ]],
   [[
      pdcch-BlindDetectionNRDC [52] SEQUENCE {
         pdcch-BlindDetectionMCG-UE [0] INTEGER (1..15),
         pdcch-BlindDetectionSCG-UE [1] INTEGER (1..15)
      } OPTIONAL,
      mux-HARQ-ACK-PUSCH-DiffSymbol [53] ENUMERATED { supported(0) } OPTIONAL
   ]],
   [[
      type1-HARQ-ACK-Codebook-r16 [54] ENUMERATED { supported(0) } OPTIONAL,
      enhancedPowerControl-r16 [55] ENUMERATED { supported(0) } OPTIONAL,
      simultaneousTCI-ActMultipleCC-r16 [56] ENUMERATED { supported(0) }
          OPTIONAL,
      simultaneousSpatialRelationMultipleCC-r16 [57] ENUMERATED { supported(0)
          } OPTIONAL,
      cli-RSSI-FDM-DL-r16 [58] ENUMERATED { supported(0) } OPTIONAL,
      cli-SRS-RSRP-FDM-DL-r16 [59] ENUMERATED { supported(0) } OPTIONAL,
      maxLayersMIMO-Adaptation-r16 [60] ENUMERATED { supported(0) } OPTIONAL,
      aggregationFactorSPS-DL-r16 [61] ENUMERATED { supported(0) } OPTIONAL,
      maxTotalResourcesForOneFreqRange-r16 [62] SEQUENCE {
         maxNumberResWithinSlotAcrossCC-OneFR-r16 [0] ENUMERATED { n2(0), n4(1)
            , n8(2), n12(3), n16(4), n32(5), n64(6), n128(7) } OPTIONAL,
         maxNumberResAcrossCC-OneFR-r16 [1] ENUMERATED { n2(0), n4(1), n8(2), 
            n12(3), n16(4), n32(5), n40(6), n48(7), n64(8), n72(9), n80(10), 
            n96(11), n128(12), n256(13) } OPTIONAL
      } OPTIONAL,
      csi-ReportFrameworkExt-r16 [63] CSI-ReportFrameworkExt-r16 OPTIONAL
   ]],
   [[
      twoTCI-Act-servingCellInCC-List-r16 [64] ENUMERATED { supported(0) }
          OPTIONAL
   ]],
   [[
      cri-RI-CQI-WithoutNon-PMI-PortInd-r16 [65] ENUMERATED { supported(0) }
          OPTIONAL
   ]],
   [[
      cqi-4-BitsSubbandTN-NonSharedSpectrumChAccess-r17 [66] ENUMERATED { 
         supported(0) } OPTIONAL
   ]],
   [[
      multipleCORESET-RedCap-r17 [67] ENUMERATED { supported(0) } OPTIONAL
   ]]
}

Phy-ParametersFR1 ::= SEQUENCE {
   pdcch-MonitoringSingleOccasion [0] ENUMERATED { supported(0) } OPTIONAL,
   scs-60kHz [1] ENUMERATED { supported(0) } OPTIONAL,
   pdsch-256QAM-FR1 [2] ENUMERATED { supported(0) } OPTIONAL,
   pdsch-RE-MappingFR1-PerSymbol [3] ENUMERATED { n10(0), n20(1) } OPTIONAL,
   ...,
   [[
      pdsch-RE-MappingFR1-PerSlot [4] ENUMERATED { n16(0), n32(1), n48(2), 
         n64(3), n80(4), n96(5), n112(6), n128(7), n144(8), n160(9), n176(10), 
         n192(11), n208(12), n224(13), n240(14), n256(15) } OPTIONAL
   ]],
   [[
      pdcch-MonitoringSingleSpanFirst4Sym-r16 [5] ENUMERATED { supported(0) }
          OPTIONAL
   ]]
}

Phy-ParametersFR2 ::= SEQUENCE {
   dummy [0] ENUMERATED { supported(0) } OPTIONAL,
   pdsch-RE-MappingFR2-PerSymbol [1] ENUMERATED { n6(0), n20(1) } OPTIONAL,
   ...,
   [[
      pCell-FR2 [2] ENUMERATED { supported(0) } OPTIONAL,
      pdsch-RE-MappingFR2-PerSlot [3] ENUMERATED { n16(0), n32(1), n48(2), 
         n64(3), n80(4), n96(5), n112(6), n128(7), n144(8), n160(9), n176(10), 
         n192(11), n208(12), n224(13), n240(14), n256(15) } OPTIONAL
   ]],
   [[
      defaultSpatialRelationPathlossRS-r16 [4] ENUMERATED { supported(0) }
          OPTIONAL,
      spatialRelationUpdateAP-SRS-r16 [5] ENUMERATED { supported(0) } OPTIONAL
         ,
      maxNumberSRS-PosSpatialRelationsAllServingCells-r16 [6] ENUMERATED { 
         n0(0), n1(1), n2(2), n4(3), n8(4), n16(5) } OPTIONAL
   ]]
}

-- TAG-PDCP-PARAMETERSMRDC-STOP
-- TAG-PHY-PARAMETERS-START
Phy-Parameters ::= SEQUENCE {
   phy-ParametersCommon [0] Phy-ParametersCommon OPTIONAL,
   phy-ParametersXDD-Diff [1] Phy-ParametersXDD-Diff OPTIONAL,
   phy-ParametersFRX-Diff [2] Phy-ParametersFRX-Diff OPTIONAL,
   phy-ParametersFR1 [3] Phy-ParametersFR1 OPTIONAL,
   phy-ParametersFR2 [4] Phy-ParametersFR2 OPTIONAL
}

UE-NR-CapabilityAddXDD-Mode ::= SEQUENCE {
   phy-ParametersXDD-Diff [0] Phy-ParametersXDD-Diff OPTIONAL,
   mac-ParametersXDD-Diff [1] MAC-ParametersXDD-Diff OPTIONAL,
   measAndMobParametersXDD-Diff [2] MeasAndMobParametersXDD-Diff OPTIONAL
}

UE-NR-CapabilityAddFRX-Mode ::= SEQUENCE {
   phy-ParametersFRX-Diff [0] Phy-ParametersFRX-Diff OPTIONAL,
   measAndMobParametersFRX-Diff [1] MeasAndMobParametersFRX-Diff OPTIONAL
}

-- TAG-SUPPORTEDBANDWIDTH-STOP
-- TAG-UE-BASEDPERFMEAS-PARAMETERS-START
UE-BasedPerfMeas-Parameters-r16 ::= SEQUENCE {
   barometerMeasReport-r16 [0] ENUMERATED { supported(0) } OPTIONAL,
   immMeasBT-r16 [1] ENUMERATED { supported(0) } OPTIONAL,
   immMeasWLAN-r16 [2] ENUMERATED { supported(0) } OPTIONAL,
   loggedMeasBT-r16 [3] ENUMERATED { supported(0) } OPTIONAL,
   loggedMeasurements-r16 [4] ENUMERATED { supported(0) } OPTIONAL,
   loggedMeasWLAN-r16 [5] ENUMERATED { supported(0) } OPTIONAL,
   orientationMeasReport-r16 [6] ENUMERATED { supported(0) } OPTIONAL,
   speedMeasReport-r16 [7] ENUMERATED { supported(0) } OPTIONAL,
   gnss-Location-r16 [8] ENUMERATED { supported(0) } OPTIONAL,
   ulPDCP-Delay-r16 [9] ENUMERATED { supported(0) } OPTIONAL,
   ...,
   [[
      sigBasedLogMDT-OverrideProtect-r17 [10] ENUMERATED { supported(0) }
          OPTIONAL,
      multipleCEF-Report-r17 [11] ENUMERATED { supported(0) } OPTIONAL,
      excessPacketDelay-r17 [12] ENUMERATED { supported(0) } OPTIONAL,
      earlyMeasLog-r17 [13] ENUMERATED { supported(0) } OPTIONAL
   ]]
}

-- TAG-SIMULTANEOUSRXTXPERBANDPAIR-STOP
-- TAG-SON-PARAMETERS-START
SON-Parameters-r16 ::= SEQUENCE {
   rach-Report-r16 [0] ENUMERATED { supported(0) } OPTIONAL,
   ...,
   [[
      rlfReportCHO-r17 [1] ENUMERATED { supported(0) } OPTIONAL,
      rlfReportDAPS-r17 [2] ENUMERATED { supported(0) } OPTIONAL,
      success-HO-Report-r17 [3] ENUMERATED { supported(0) } OPTIONAL,
      twoStepRACH-Report-r17 [4] ENUMERATED { supported(0) } OPTIONAL,
      pscell-MHI-Report-r17 [5] ENUMERATED { supported(0) } OPTIONAL,
      onDemandSI-Report-r17 [6] ENUMERATED { supported(0) } OPTIONAL
   ]]
}

-- TAG-NRDC-PARAMETERS-STOP
-- TAG-NTN-PARAMETERS-START
NTN-Parameters-r17 ::= SEQUENCE {
   inactiveStateNTN-r17 [0] ENUMERATED { supported(0) } OPTIONAL,
   ra-SDT-NTN-r17 [1] ENUMERATED { supported(0) } OPTIONAL,
   srb-SDT-NTN-r17 [2] ENUMERATED { supported(0) } OPTIONAL,
   measAndMobParametersNTN-r17 [3] MeasAndMobParameters OPTIONAL,
   mac-ParametersNTN-r17 [4] MAC-Parameters OPTIONAL,
   phy-ParametersNTN-r17 [5] Phy-Parameters OPTIONAL,
   fdd-Add-UE-NR-CapabilitiesNTN-r17 [6] UE-NR-CapabilityAddXDD-Mode OPTIONAL,
   fr1-Add-UE-NR-CapabilitiesNTN-r17 [7] UE-NR-CapabilityAddFRX-Mode OPTIONAL,
   ue-BasedPerfMeas-ParametersNTN-r17 [8] UE-BasedPerfMeas-Parameters-r16
       OPTIONAL,
   son-ParametersNTN-r17 [9] SON-Parameters-r16 OPTIONAL
}

-- TAG-NTN-PARAMETERS-STOP
-- TAG-OLPC-SRS-POS-START
OLPC-SRS-Pos-r16 ::= SEQUENCE {
   olpc-SRS-PosBasedOnPRS-Serving-r16 [0] ENUMERATED { supported(0) } OPTIONAL,
   olpc-SRS-PosBasedOnSSB-Neigh-r16 [1] ENUMERATED { supported(0) } OPTIONAL,
   olpc-SRS-PosBasedOnPRS-Neigh-r16 [2] ENUMERATED { supported(0) } OPTIONAL,
   maxNumberPathLossEstimatePerServing-r16 [3] ENUMERATED { n1(0), n4(1), n8(2)
      , n16(3) } OPTIONAL
}

--TAG-OLPC-SRS-POS-STOP
-- TAG-PDCP-PARAMETERS-START
PDCP-Parameters ::= SEQUENCE {
   supportedROHC-Profiles [0] SEQUENCE {
      profile0x0000 [0] BOOLEAN,
      profile0x0001 [1] BOOLEAN,
      profile0x0002 [2] BOOLEAN,
      profile0x0003 [3] BOOLEAN,
      profile0x0004 [4] BOOLEAN,
      profile0x0006 [5] BOOLEAN,
      profile0x0101 [6] BOOLEAN,
      profile0x0102 [7] BOOLEAN,
      profile0x0103 [8] BOOLEAN,
      profile0x0104 [9] BOOLEAN
   },
   maxNumberROHC-ContextSessions [1] ENUMERATED { cs2(0), cs4(1), cs8(2), 
      cs12(3), cs16(4), cs24(5), cs32(6), cs48(7), cs64(8), cs128(9), cs256(10)
      , cs512(11), cs1024(12), cs16384(13), spare2(14), spare1(15) },
   uplinkOnlyROHC-Profiles [2] ENUMERATED { supported(0) } OPTIONAL,
   continueROHC-Context [3] ENUMERATED { supported(0) } OPTIONAL,
   outOfOrderDelivery [4] ENUMERATED { supported(0) } OPTIONAL,
   shortSN [5] ENUMERATED { supported(0) } OPTIONAL,
   pdcp-DuplicationSRB [6] ENUMERATED { supported(0) } OPTIONAL,
   pdcp-DuplicationMCG-OrSCG-DRB [7] ENUMERATED { supported(0) } OPTIONAL,
   ...,
   [[
      drb-IAB-r16 [8] ENUMERATED { supported(0) } OPTIONAL,
      non-DRB-IAB-r16 [9] ENUMERATED { supported(0) } OPTIONAL,
      extendedDiscardTimer-r16 [10] ENUMERATED { supported(0) } OPTIONAL,
      continueEHC-Context-r16 [11] ENUMERATED { supported(0) } OPTIONAL,
      ehc-r16 [12] ENUMERATED { supported(0) } OPTIONAL,
      maxNumberEHC-Contexts-r16 [13] ENUMERATED { cs2(0), cs4(1), cs8(2), 
         cs16(3), cs32(4), cs64(5), cs128(6), cs256(7), cs512(8), cs1024(9), 
         cs2048(10), cs4096(11), cs8192(12), cs16384(13), cs32768(14), 
         cs65536(15) } OPTIONAL,
      jointEHC-ROHC-Config-r16 [14] ENUMERATED { supported(0) } OPTIONAL,
      pdcp-DuplicationMoreThanTwoRLC-r16 [15] ENUMERATED { supported(0) }
          OPTIONAL
   ]],
   [[
      longSN-RedCap-r17 [16] ENUMERATED { supported(0) } OPTIONAL,
      udc-r17 [17] SEQUENCE {
         standardDictionary-r17 [0] ENUMERATED { supported(0) } OPTIONAL,
         operatorDictionary-r17 [1] SEQUENCE {
            versionOfDictionary-r17 [0] INTEGER (0..15),
            associatedPLMN-ID-r17 [1] PLMN-Identity
         } OPTIONAL,
         continueUDC-r17 [2] ENUMERATED { supported(0) } OPTIONAL,
         supportOfBufferSize-r17 [3] ENUMERATED { kbyte4(0), kbyte8(1) }
             OPTIONAL
      } OPTIONAL
   ]]
}

-- TAG-PDCP-PARAMETERS-STOP
-- TAG-PDCP-PARAMETERSMRDC-START
PDCP-ParametersMRDC ::= SEQUENCE {
   pdcp-DuplicationSplitSRB [0] ENUMERATED { supported(0) } OPTIONAL,
   pdcp-DuplicationSplitDRB [1] ENUMERATED { supported(0) } OPTIONAL
}

PDCP-ParametersMRDC-v1610 ::= SEQUENCE {
   scg-DRB-NR-IAB-r16 [0] ENUMERATED { supported(0) } OPTIONAL
}

Phy-ParametersCommon-v16a0 ::= SEQUENCE {
   srs-PeriodicityAndOffsetExt-r16 [0] ENUMERATED { supported(0) } OPTIONAL
}

Phy-Parameters-v16a0 ::= SEQUENCE {
   phy-ParametersCommon-v16a0 [0] Phy-ParametersCommon-v16a0 OPTIONAL
}

NAICS-Capability-Entry ::= SEQUENCE {
   numberOfNAICS-CapableCC [0] INTEGER (1..5),
   numberOfAggregatedPRB [1] ENUMERATED { n50(0), n75(1), n100(2), n125(3), 
      n150(4), n175(5), n200(6), n225(7), n250(8), n275(9), n300(10), n350(11)
      , n400(12), n450(13), n500(14), spare(15) },
   ...
}

-- TAG-PHY-PARAMETERS-STOP
-- TAG-PHY-PARAMETERSMRDC-START
Phy-ParametersMRDC ::= SEQUENCE {
   naics-Capability-List [0] SEQUENCE (SIZE (1..maxNrofNAICS-Entries)) OF NAICS-Capability-Entry
       OPTIONAL,
   ...,
   [[
      spCellPlacement [1] CarrierAggregationVariant OPTIONAL
   ]],
   [[
      tdd-PCellUL-TX-AllUL-Subframe-r16 [2] ENUMERATED { supported(0) }
          OPTIONAL,
      fdd-PCellUL-TX-AllUL-Subframe-r16 [3] ENUMERATED { supported(0) }
          OPTIONAL
   ]]
}

-- TAG-PHY-PARAMETERSMRDC-STOP
-- TAG-PHY-PARAMETERSSHAREDSPECTRUMCHACCESS-START
Phy-ParametersSharedSpectrumChAccess-r16 ::= SEQUENCE {
     -- 10-32 (1-2): SS block based SINR measurement (SS-SINR) for unlicensed spectrum
   ss-SINR-Meas-r16 [0] ENUMERATED { supported(0) } OPTIONAL,
     -- 10-33 (2-32a): Semi-persistent CSI report on PUCCH for unlicensed spectrum
   sp-CSI-ReportPUCCH-r16 [1] ENUMERATED { supported(0) } OPTIONAL,
     -- 10-33a (2-32b): Semi-persistent CSI report on PUSCH for unlicensed spectrum
   sp-CSI-ReportPUSCH-r16 [2] ENUMERATED { supported(0) } OPTIONAL,
     -- 10-34 (3-6): Dynamic SFI monitoring for unlicensed spectrum
   dynamicSFI-r16 [3] ENUMERATED { supported(0) } OPTIONAL,
     -- 10-35c (4-19c): SR/HARQ-ACK/CSI multiplexing once per slot using a PUCCH (or HARQ-ACK/CSI piggybacked on a PUSCH) when SR/HARQ-
     -- ACK/CSI are supposed to be sent with different starting symbols in a slot for unlicensed spectrum
     -- 10-35 (4-19): SR/HARQ-ACK/CSI multiplexing once per slot using a PUCCH (or HARQ-ACK/CSI piggybacked on a PUSCH) when SR/HARQ-
     -- ACK/CSI are supposed to be sent with the same starting symbol on the PUCCH resources in a slot for unlicensed spectrum
   mux-SR-HARQ-ACK-CSI-PUCCH-OncePerSlot-r16 [4] SEQUENCE {
      sameSymbol-r16 [0] ENUMERATED { supported(0) } OPTIONAL,
      diffSymbol-r16 [1] ENUMERATED { supported(0) } OPTIONAL
   } OPTIONAL,
     -- 10-35a (4-19a): Overlapping PUCCH resources have different starting symbols in a slot for unlicensed spectrum
   mux-SR-HARQ-ACK-PUCCH-r16 [5] ENUMERATED { supported(0) } OPTIONAL,
     -- 10-35b (4-19b): SR/HARQ-ACK/CSI multiplexing more than once per slot using a PUCCH (or HARQ-ACK/CSI piggybacked on a PUSCH) when
     -- SR/HARQ ACK/CSI are supposed to be sent with the same or different starting symbol in a slot for unlicensed spectrum
   mux-SR-HARQ-ACK-CSI-PUCCH-MultiPerSlot-r16 [6] ENUMERATED { supported(0) }
       OPTIONAL,
     -- 10-36 (4-28): HARQ-ACK multiplexing on PUSCH with different PUCCH/PUSCH starting OFDM symbols for unlicensed spectrum
   mux-HARQ-ACK-PUSCH-DiffSymbol-r16 [7] ENUMERATED { supported(0) } OPTIONAL,
     -- 10-37 (4-23): Repetitions for PUCCH format 1, 3, and 4 over multiple slots with K = 2, 4, 8 for unlicensed spectrum
   pucch-Repetition-F1-3-4-r16 [8] ENUMERATED { supported(0) } OPTIONAL,
     -- 10-38 (5-14): Type 1 configured PUSCH repetitions over multiple slots for unlicensed spectrum
   type1-PUSCH-RepetitionMultiSlots-r16 [9] ENUMERATED { supported(0) }
       OPTIONAL,
     -- 10-39 (5-16): Type 2 configured PUSCH repetitions over multiple slots for unlicensed spectrum
   type2-PUSCH-RepetitionMultiSlots-r16 [10] ENUMERATED { supported(0) }
       OPTIONAL,
     -- 10-40 (5-17): PUSCH repetitions over multiple slots for unlicensed spectrum
   pusch-RepetitionMultiSlots-r16 [11] ENUMERATED { supported(0) } OPTIONAL,
     -- 10-40a (5-17a): PDSCH repetitions over multiple slots for unlicensed spectrum
   pdsch-RepetitionMultiSlots-r16 [12] ENUMERATED { supported(0) } OPTIONAL,
     -- 10-41 (5-18): DL SPS
   downlinkSPS-r16 [13] ENUMERATED { supported(0) } OPTIONAL,
     -- 10-42 (5-19): Type 1 Configured UL grant
   configuredUL-GrantType1-r16 [14] ENUMERATED { supported(0) } OPTIONAL,
     -- 10-43 (5-20): Type 2 Configured UL grant
   configuredUL-GrantType2-r16 [15] ENUMERATED { supported(0) } OPTIONAL,
     -- 10-44 (5-21): Pre-emption indication for DL
   pre-EmptIndication-DL-r16 [16] ENUMERATED { supported(0) } OPTIONAL,
   ...
}

-- TAG-PHY-PARAMETERSSHAREDSPECTRUMCHACCESS-STOP
-- TAG-POSSRS-RRC-INACTIVE-OUTSIDEINITIALUL-BWP-START
PosSRS-RRC-Inactive-OutsideInitialUL-BWP-r17 ::= SEQUENCE {
     -- R1 27-15b: Positioning SRS transmission in RRC_INACTIVE state configured outside initial UL BWP
   maxSRSposBandwidthForEachSCS-withinCC-FR1-r17 [0] ENUMERATED { mhz5(0), 
      mhz10(1), mhz15(2), mhz20(3), mhz25(4), mhz30(5), mhz35(6), mhz40(7), 
      mhz45(8), mhz50(9), mhz60(10), mhz70(11), mhz80(12), mhz90(13), 
      mhz100(14) } OPTIONAL,
   maxSRSposBandwidthForEachSCS-withinCC-FR2-r17 [1] ENUMERATED { mhz50(0), 
      mhz100(1), mhz200(2), mhz400(3) } OPTIONAL,
   maxNumOfSRSposResourceSets-r17 [2] ENUMERATED { n1(0), n2(1), n4(2), n8(3), 
      n12(4), n16(5) } OPTIONAL,
   maxNumOfPeriodicSRSposResources-r17 [3] ENUMERATED { n1(0), n2(1), n4(2), 
      n8(3), n16(4), n32(5), n64(6) } OPTIONAL,
   maxNumOfPeriodicSRSposResourcesPerSlot-r17 [4] ENUMERATED { n1(0), n2(1), 
      n3(2), n4(3), n5(4), n6(5), n8(6), n10(7), n12(8), n14(9) } OPTIONAL,
   differentNumerologyBetweenSRSposAndInitialBWP-r17 [5] ENUMERATED { 
      supported(0) } OPTIONAL,
   srsPosWithoutRestrictionOnBWP-r17 [6] ENUMERATED { supported(0) } OPTIONAL,
   maxNumOfPeriodicAndSemipersistentSRSposResources-r17 [7] ENUMERATED { n1(0)
      , n2(1), n4(2), n8(3), n16(4), n32(5), n64(6) } OPTIONAL,
   maxNumOfPeriodicAndSemipersistentSRSposResourcesPerSlot-r17 [8] ENUMERATED
       { n1(0), n2(1), n3(2), n4(3), n5(4), n6(5), n8(6), n10(7), n12(8), 
      n14(9) } OPTIONAL,
   differentCenterFreqBetweenSRSposAndInitialBWP-r17 [9] ENUMERATED { 
      supported(0) } OPTIONAL,
   switchingTimeSRS-TX-OtherTX-r17 [10] ENUMERATED { us100(0), us140(1), 
      us200(2), us300(3), us500(4) } OPTIONAL,
     -- R1 27-15c: Support of positioning SRS transmission in RRC_INACTIVE state outside initial BWP with semi-persistent SRS
   maxNumOfSemiPersistentSRSposResources-r17 [11] ENUMERATED { n1(0), n2(1), 
      n4(2), n8(3), n16(4), n32(5), n64(6) } OPTIONAL,
   maxNumOfSemiPersistentSRSposResourcesPerSlot-r17 [12] ENUMERATED { n1(0), 
      n2(1), n3(2), n4(3), n5(4), n6(5), n8(6), n10(7), n12(8), n14(9) }
       OPTIONAL,
   ...
}

PowSav-ParametersCommon-r16 ::= SEQUENCE {
   drx-Preference-r16 [0] ENUMERATED { supported(0) } OPTIONAL,
   maxCC-Preference-r16 [1] ENUMERATED { supported(0) } OPTIONAL,
   releasePreference-r16 [2] ENUMERATED { supported(0) } OPTIONAL,
     -- R1 19-4a: UE assistance information
   minSchedulingOffsetPreference-r16 [3] ENUMERATED { supported(0) } OPTIONAL,
   ...
}

PowSav-ParametersFRX-Diff-r16 ::= SEQUENCE {
   maxBW-Preference-r16 [0] ENUMERATED { supported(0) } OPTIONAL,
   maxMIMO-LayerPreference-r16 [1] ENUMERATED { supported(0) } OPTIONAL,
   ...
}

-- TAG-POSSRS-RRC-INACTIVE-OUTSIDEINITIALUL-BWP-STOP
-- TAG-POWSAV-PARAMETERS-START
PowSav-Parameters-r16 ::= SEQUENCE {
   powSav-ParametersCommon-r16 [0] PowSav-ParametersCommon-r16 OPTIONAL,
   powSav-ParametersFRX-Diff-r16 [1] PowSav-ParametersFRX-Diff-r16 OPTIONAL,
   ...
}

PowSav-ParametersFR2-2-r17 ::= SEQUENCE {
   maxBW-Preference-r17 [0] ENUMERATED { supported(0) } OPTIONAL,
   maxMIMO-LayerPreference-r17 [1] ENUMERATED { supported(0) } OPTIONAL,
   ...
}

PowSav-Parameters-v1700 ::= SEQUENCE {
   powSav-ParametersFR2-2-r17 [0] PowSav-ParametersFR2-2-r17 OPTIONAL,
   ...
}

-- TAG-PROCESSINGPARAMETERS-STOP
-- TAG-PRS-PROCESSINGCAPABILITYOUTSIDEMGINPPWPERType-START
PRS-ProcessingCapabilityOutsideMGinPPWperType-r17 ::= SEQUENCE {
   prsProcessingType-r17 [0] ENUMERATED { type1A(0), type1B(1), type2(2) },
   ppw-dl-PRS-BufferType-r17 [1] ENUMERATED { type1(0), type2(1), ... },
   ppw-durationOfPRS-Processing-r17 [2] EXPLICIT CHOICE {
      ppw-durationOfPRS-Processing1-r17 [0] SEQUENCE {
         ppw-durationOfPRS-ProcessingSymbolsN-r17 [0] ENUMERATED { msDot125(0)
            , msDot25(1), msDot5(2), ms1(3), ms2(4), ms4(5), ms6(6), ms8(7), 
            ms12(8), ms16(9), ms20(10), ms25(11), ms30(12), ms32(13), ms35(14)
            , ms40(15), ms45(16), ms50(17) },
         ppw-durationOfPRS-ProcessingSymbolsT-r17 [1] ENUMERATED { ms1(0), 
            ms2(1), ms4(2), ms8(3), ms16(4), ms20(5), ms30(6), ms40(7), ms80(8)
            , ms160(9), ms320(10), ms640(11), ms1280(12) }
      },
      ppw-durationOfPRS-Processing2-r17 [1] SEQUENCE {
         ppw-durationOfPRS-ProcessingSymbolsN2-r17 [0] ENUMERATED { msDot125(0)
            , msDot25(1), msDot5(2), ms1(3), ms2(4), ms3(5), ms4(6), ms5(7), 
            ms6(8), ms8(9), ms12(10) },
         ppw-durationOfPRS-ProcessingSymbolsT2-r17 [1] ENUMERATED { ms4(0), 
            ms5(1), ms6(2), ms8(3) }
      }
   } OPTIONAL,
   ppw-maxNumOfDL-PRS-ResProcessedPerSlot-r17 [3] SEQUENCE {
      scs15-r17 [0] ENUMERATED { n1(0), n2(1), n4(2), n6(3), n8(4), n12(5), 
         n16(6), n24(7), n32(8), n48(9), n64(10) } OPTIONAL,
      scs30-r17 [1] ENUMERATED { n1(0), n2(1), n4(2), n6(3), n8(4), n12(5), 
         n16(6), n24(7), n32(8), n48(9), n64(10) } OPTIONAL,
      scs60-r17 [2] ENUMERATED { n1(0), n2(1), n4(2), n6(3), n8(4), n12(5), 
         n16(6), n24(7), n32(8), n48(9), n64(10) } OPTIONAL,
      scs120-r17 [3] ENUMERATED { n1(0), n2(1), n4(2), n6(3), n8(4), n12(5), 
         n16(6), n24(7), n32(8), n48(9), n64(10) } OPTIONAL,
      ...
   },
   ppw-maxNumOfDL-Bandwidth-r17 [4] EXPLICIT CHOICE {
      fr1-r17 [0] ENUMERATED { mhz5(0), mhz10(1), mhz20(2), mhz40(3), mhz50(4)
         , mhz80(5), mhz100(6) },
      fr2-r17 [1] ENUMERATED { mhz50(0), mhz100(1), mhz200(2), mhz400(3) }
   } OPTIONAL
}

-- TAG-RAT-TYPE-STOP
-- TAG-REDCAPPARAMETERS-START
RedCapParameters-r17 ::= SEQUENCE {
     -- R1 28-1: RedCap UE
   supportOfRedCap-r17 [0] ENUMERATED { supported(0) } OPTIONAL,
   supportOf16DRB-RedCap-r17 [1] ENUMERATED { supported(0) } OPTIONAL
}

RedCapParameters-v1740 ::= SEQUENCE {
   ncd-SSB-ForRedCapInitialBWP-SDT-r17 [0] ENUMERATED { supported(0) } OPTIONAL
}

-- TAG-UE-RADIOPAGINGINFO-STOP
-- TAG-SHAREDSPECTRUMCHACCESSPARAMSPERBAND-START
SharedSpectrumChAccessParamsPerBand-r16 ::= SEQUENCE {
     -- R1 10-1: UL channel access for dynamic channel access mode
   ul-DynamicChAccess-r16 [0] ENUMERATED { supported(0) } OPTIONAL,
     -- R1 10-1a: UL channel access for semi-static channel access mode
   ul-Semi-StaticChAccess-r16 [1] ENUMERATED { supported(0) } OPTIONAL,
     -- R1 10-2: SSB-based RRM for dynamic channel access mode
   ssb-RRM-DynamicChAccess-r16 [2] ENUMERATED { supported(0) } OPTIONAL,
     -- R1 10-2a: SSB-based RRM for semi-static channel access mode
   ssb-RRM-Semi-StaticChAccess-r16 [3] ENUMERATED { supported(0) } OPTIONAL,
     -- R1 10-2b: MIB reading on unlicensed cell
   mib-Acquisition-r16 [4] ENUMERATED { supported(0) } OPTIONAL,
     -- R1 10-2c: SSB-based RLM for dynamic channel access mode
   ssb-RLM-DynamicChAccess-r16 [5] ENUMERATED { supported(0) } OPTIONAL,
     -- R1 10-2d: SSB-based RLM for semi-static channel access mode
   ssb-RLM-Semi-StaticChAccess-r16 [6] ENUMERATED { supported(0) } OPTIONAL,
     -- R1 10-2e: SIB1 reception on unlicensed cell
   sib1-Acquisition-r16 [7] ENUMERATED { supported(0) } OPTIONAL,
     -- R1 10-2f: Support monitoring of extended RAR window
   extRA-ResponseWindow-r16 [8] ENUMERATED { supported(0) } OPTIONAL,
     -- R1 10-2g: SSB-based BFD/CBD for dynamic channel access mode
   ssb-BFD-CBD-dynamicChannelAccess-r16 [9] ENUMERATED { supported(0) }
       OPTIONAL,
     -- R1 10-2h: SSB-based BFD/CBD for semi-static channel access mode
   ssb-BFD-CBD-semi-staticChannelAccess-r16 [10] ENUMERATED { supported(0) }
       OPTIONAL,
     -- R1 10-2i: CSI-RS-based BFD/CBD for NR-U
   csi-RS-BFD-CBD-r16 [11] ENUMERATED { supported(0) } OPTIONAL,
     -- R1 10-7: UL channel access for 10 MHz SCell
   ul-ChannelBW-SCell-10mhz-r16 [12] ENUMERATED { supported(0) } OPTIONAL,
     -- R1 10-10: RSSI and channel occupancy measurement and reporting
   rssi-ChannelOccupancyReporting-r16 [13] ENUMERATED { supported(0) } OPTIONAL
      ,
     -- R1 10-11:SRS starting position at any OFDM symbol in a slot
   srs-StartAnyOFDM-Symbol-r16 [14] ENUMERATED { supported(0) } OPTIONAL,
     -- R1 10-20: Support search space set configuration with freqMonitorLocation-r16
   searchSpaceFreqMonitorLocation-r16 [15] INTEGER (1..5) OPTIONAL,
     -- R1 10-20a: Support coreset configuration with rb-Offset
   coreset-RB-Offset-r16 [16] ENUMERATED { supported(0) } OPTIONAL,
     -- R1 10-23:CGI reading on unlicensed cell for ANR functionality
   cgi-Acquisition-r16 [17] ENUMERATED { supported(0) } OPTIONAL,
     -- R1 10-25: Enable configured UL transmissions when DCI 2_0 is configured but not detected
   configuredUL-Tx-r16 [18] ENUMERATED { supported(0) } OPTIONAL,
     -- R1 10-27: Wideband PRACH
   prach-Wideband-r16 [19] ENUMERATED { supported(0) } OPTIONAL,
     -- R1 10-29: Support available RB set indicator field in DCI 2_0
   dci-AvailableRB-Set-r16 [20] ENUMERATED { supported(0) } OPTIONAL,
     -- R1 10-30: Support channel occupancy duration indicator field in DCI 2_0
   dci-ChOccupancyDuration-r16 [21] ENUMERATED { supported(0) } OPTIONAL,
     -- R1 10-8: Type B PDSCH length {3, 5, 6, 8, 9, 10, 11, 12, 13} without DMRS shift due to CRS collision
   typeB-PDSCH-length-r16 [22] ENUMERATED { supported(0) } OPTIONAL,
     -- R1 10-9: Search space set group switching with explicit DCI 2_0 bit field trigger or with implicit PDCCH decoding with DCI 2_0 monitoring
   searchSpaceSwitchWithDCI-r16 [23] ENUMERATED { supported(0) } OPTIONAL,
     -- R1 10-9b: Search space set group switching with implicit PDCCH decoding without DCI 2_0 monitoring
   searchSpaceSwitchWithoutDCI-r16 [24] ENUMERATED { supported(0) } OPTIONAL,
     -- R1 10-9d: Support Search space set group switching capability 2
   searchSpaceSwitchCapability2-r16 [25] ENUMERATED { supported(0) } OPTIONAL,
     -- R1 10-14: Non-numerical PDSCH to HARQ-ACK timing
   non-numericalPDSCH-HARQ-timing-r16 [26] ENUMERATED { supported(0) } OPTIONAL
      ,
     -- R1 10-15: Enhanced dynamic HARQ codebook
   enhancedDynamicHARQ-codebook-r16 [27] ENUMERATED { supported(0) } OPTIONAL,
     -- R1 10-16: One-shot HARQ ACK feedback
   oneShotHARQ-feedback-r16 [28] ENUMERATED { supported(0) } OPTIONAL,
     -- R1 10-17: Multi-PUSCH UL grant
   multiPUSCH-UL-grant-r16 [29] ENUMERATED { supported(0) } OPTIONAL,
     -- R1 10-26: CSI-RS based RLM for NR-U
   csi-RS-RLM-r16 [30] ENUMERATED { supported(0) } OPTIONAL,
   dummy [31] ENUMERATED { supported(0) } OPTIONAL,
     -- R1 10-31: Support of P/SP-CSI-RS reception with CSI-RS-ValidationWith-DCI-r16 configured
   periodicAndSemi-PersistentCSI-RS-r16 [32] ENUMERATED { supported(0) }
       OPTIONAL,
     -- R1 10-3: PRB interlace mapping for PUSCH
   pusch-PRB-interlace-r16 [33] ENUMERATED { supported(0) } OPTIONAL,
     -- R1 10-3a: PRB interlace mapping for PUCCH
   pucch-F0-F1-PRB-Interlace-r16 [34] ENUMERATED { supported(0) } OPTIONAL,
     -- R1 10-12: OCC for PRB interlace mapping for PF2 and PF3
   occ-PRB-PF2-PF3-r16 [35] ENUMERATED { supported(0) } OPTIONAL,
     -- R1 10-13a: Extended CP range of more than one symbol for CG-PUSCH
   extCP-rangeCG-PUSCH-r16 [36] ENUMERATED { supported(0) } OPTIONAL,
     -- R1 10-18: Configured grant with retransmission in CG resources
   configuredGrantWithReTx-r16 [37] ENUMERATED { supported(0) } OPTIONAL,
     -- R1 10-21a: Support using ED threshold given by gNB for UL to DL COT sharing
   ed-Threshold-r16 [38] ENUMERATED { supported(0) } OPTIONAL,
     -- R1 10-21b: Support UL to DL COT sharing
   ul-DL-COT-Sharing-r16 [39] ENUMERATED { supported(0) } OPTIONAL,
     -- R1 10-24: CG-UCI multiplexing with HARQ ACK
   mux-CG-UCI-HARQ-ACK-r16 [40] ENUMERATED { supported(0) } OPTIONAL,
     -- R1 10-28: Configured grant with Rel-16 enhanced resource configuration
   cg-resourceConfig-r16 [41] ENUMERATED { supported(0) } OPTIONAL
}

-- TAG-SON-PARAMETERS-STOP
-- TAG-SPATIALRELATIONSSRS-POS-START
SpatialRelationsSRS-Pos-r16 ::= SEQUENCE {
   spatialRelation-SRS-PosBasedOnSSB-Serving-r16 [0] ENUMERATED { supported(0)
       } OPTIONAL,
   spatialRelation-SRS-PosBasedOnCSI-RS-Serving-r16 [1] ENUMERATED { 
      supported(0) } OPTIONAL,
   spatialRelation-SRS-PosBasedOnPRS-Serving-r16 [2] ENUMERATED { supported(0)
       } OPTIONAL,
   spatialRelation-SRS-PosBasedOnSRS-r16 [3] ENUMERATED { supported(0) }
       OPTIONAL,
   spatialRelation-SRS-PosBasedOnSSB-Neigh-r16 [4] ENUMERATED { supported(0) }
       OPTIONAL,
   spatialRelation-SRS-PosBasedOnPRS-Neigh-r16 [5] ENUMERATED { supported(0) }
       OPTIONAL
}

SharedSpectrumChAccessParamsPerBand-v1630 ::= SEQUENCE {
     -- R4 4-1: DL reception in intra-carrier guardband
   dl-ReceptionIntraCellGuardband-r16 [0] ENUMERATED { supported(0) } OPTIONAL,
     -- R4 4-2: DL reception when gNB does not transmit on all RB sets of a carrier as a result of LBT
   dl-ReceptionLBT-subsetRB-r16 [1] ENUMERATED { supported(0) } OPTIONAL
}

SharedSpectrumChAccessParamsPerBand-v1640 ::= SEQUENCE {
     -- 10-26b(1-4): CSI-RS based RRM measurement with associated SS-block
   csi-RSRP-AndRSRQ-MeasWithSSB-r16 [0] ENUMERATED { supported(0) } OPTIONAL,
     -- 10-26c(1-5): CSI-RS based RRM measurement without associated SS-block
   csi-RSRP-AndRSRQ-MeasWithoutSSB-r16 [1] ENUMERATED { supported(0) } OPTIONAL
      ,
     -- 10-26d(1-6): CSI-RS based RS-SINR measurement
   csi-SINR-Meas-r16 [2] ENUMERATED { supported(0) } OPTIONAL,
     -- 10-26e(1-8): RLM based on a mix of SS block and CSI-RS signals within active BWP
   ssb-AndCSI-RS-RLM-r16 [3] ENUMERATED { supported(0) } OPTIONAL,
     -- 10-26f(1-9): CSI-RS based contention free RA for HO
   csi-RS-CFRA-ForHO-r16 [4] ENUMERATED { supported(0) } OPTIONAL
}

SharedSpectrumChAccessParamsPerBand-v1650 ::= SEQUENCE {
     -- Extension of R1 10-9 capability to configure up to 16 instead of 4 cells or cell groups, respectively
   extendedSearchSpaceSwitchWithDCI-r16 [0] ENUMERATED { supported(0) }
       OPTIONAL
}

--TAG-SPATIALRELATIONSSRS-POS-STOP
-- TAG-SRS-ALLPOSRESOURCESRRC-INACTIVE-START
SRS-AllPosResourcesRRC-Inactive-r17 ::= SEQUENCE {
   srs-PosResourcesRRC-Inactive-r17 [0] SEQUENCE {
      -- R1 27-15: Positioning SRS transmission in RRC_INACTIVE state for initial UL BWP
      maxNumberSRS-PosResourceSetPerBWP-r17 [0] ENUMERATED { n1(0), n2(1), 
         n4(2), n8(3), n12(4), n16(5) },
      maxNumberSRS-PosResourcesPerBWP-r17 [1] ENUMERATED { n1(0), n2(1), n4(2)
         , n8(3), n16(4), n32(5), n64(6) },
      maxNumberSRS-ResourcesPerBWP-PerSlot-r17 [2] ENUMERATED { n1(0), n2(1), 
         n3(2), n4(3), n5(4), n6(5), n8(6), n10(7), n12(8), n14(9) },
      maxNumberPeriodicSRS-PosResourcesPerBWP-r17 [3] ENUMERATED { n1(0), n2(1)
         , n4(2), n8(3), n16(4), n32(5), n64(6) },
      maxNumberPeriodicSRS-PosResourcesPerBWP-PerSlot-r17 [4] ENUMERATED { 
         n1(0), n2(1), n3(2), n4(3), n5(4), n6(5), n8(6), n10(7), n12(8), 
         n14(9) },
      dummy1 [5] ENUMERATED { n1(0), n2(1), n4(2), n8(3), n16(4), n32(5), 
         n64(6) },
      dummy2 [6] ENUMERATED { n1(0), n2(1), n3(2), n4(3), n5(4), n6(5), n8(6), 
         n10(7), n12(8), n14(9) }
   }
}

SharedSpectrumChAccessParamsPerBand-v1710 ::= SEQUENCE {
     -- R1 25-12: UE initiated semi-static channel occupancy with dependent configurations
   ul-Semi-StaticChAccessDependentConfig-r17 [0] ENUMERATED { supported(0) }
       OPTIONAL,
     -- R1 25-13: UE initiated semi-static channel occupancy with independent configurations
   ul-Semi-StaticChAccessIndependentConfig-r17 [1] ENUMERATED { supported(0) }
       OPTIONAL
}

BandNR ::= SEQUENCE {
   bandNR [0] FreqBandIndicatorNR,
   modifiedMPR-Behaviour [1] BIT STRING  (SIZE (8)) OPTIONAL,
   mimo-ParametersPerBand [2] MIMO-ParametersPerBand OPTIONAL,
   extendedCP [3] ENUMERATED { supported(0) } OPTIONAL,
   multipleTCI [4] ENUMERATED { supported(0) } OPTIONAL,
   bwp-WithoutRestriction [5] ENUMERATED { supported(0) } OPTIONAL,
   bwp-SameNumerology [6] ENUMERATED { upto2(0), upto4(1) } OPTIONAL,
   bwp-DiffNumerology [7] ENUMERATED { upto4(0) } OPTIONAL,
   crossCarrierScheduling-SameSCS [8] ENUMERATED { supported(0) } OPTIONAL,
   pdsch-256QAM-FR2 [9] ENUMERATED { supported(0) } OPTIONAL,
   pusch-256QAM [10] ENUMERATED { supported(0) } OPTIONAL,
   ue-PowerClass [11] ENUMERATED { pc1(0), pc2(1), pc3(2), pc4(3) } OPTIONAL,
   rateMatchingLTE-CRS [12] ENUMERATED { supported(0) } OPTIONAL,
   channelBWs-DL [13] EXPLICIT CHOICE {
      fr1 [0] SEQUENCE {
         scs-15kHz [0] BIT STRING  (SIZE (10)) OPTIONAL,
         scs-30kHz [1] BIT STRING  (SIZE (10)) OPTIONAL,
         scs-60kHz [2] BIT STRING  (SIZE (10)) OPTIONAL
      },
      fr2 [1] SEQUENCE {
         scs-60kHz [0] BIT STRING  (SIZE (3)) OPTIONAL,
         scs-120kHz [1] BIT STRING  (SIZE (3)) OPTIONAL
      }
   } OPTIONAL,
   channelBWs-UL [14] EXPLICIT CHOICE {
      fr1 [0] SEQUENCE {
         scs-15kHz [0] BIT STRING  (SIZE (10)) OPTIONAL,
         scs-30kHz [1] BIT STRING  (SIZE (10)) OPTIONAL,
         scs-60kHz [2] BIT STRING  (SIZE (10)) OPTIONAL
      },
      fr2 [1] SEQUENCE {
         scs-60kHz [0] BIT STRING  (SIZE (3)) OPTIONAL,
         scs-120kHz [1] BIT STRING  (SIZE (3)) OPTIONAL
      }
   } OPTIONAL,
   ...,
   [[
      maxUplinkDutyCycle-PC2-FR1 [15] ENUMERATED { n60(0), n70(1), n80(2), 
         n90(3), n100(4) } OPTIONAL
   ]],
   [[
      pucch-SpatialRelInfoMAC-CE [16] ENUMERATED { supported(0) } OPTIONAL,
      powerBoosting-pi2BPSK [17] ENUMERATED { supported(0) } OPTIONAL
   ]],
   [[
      maxUplinkDutyCycle-FR2 [18] ENUMERATED { n15(0), n20(1), n25(2), n30(3), 
         n40(4), n50(5), n60(6), n70(7), n80(8), n90(9), n100(10) } OPTIONAL
   ]],
   [[
      channelBWs-DL-v1590 [19] EXPLICIT CHOICE {
         fr1 [0] SEQUENCE {
            scs-15kHz [0] BIT STRING  (SIZE (16)) OPTIONAL,
            scs-30kHz [1] BIT STRING  (SIZE (16)) OPTIONAL,
            scs-60kHz [2] BIT STRING  (SIZE (16)) OPTIONAL
         },
         fr2 [1] SEQUENCE {
            scs-60kHz [0] BIT STRING  (SIZE (8)) OPTIONAL,
            scs-120kHz [1] BIT STRING  (SIZE (8)) OPTIONAL
         }
      } OPTIONAL,
      channelBWs-UL-v1590 [20] EXPLICIT CHOICE {
         fr1 [0] SEQUENCE {
            scs-15kHz [0] BIT STRING  (SIZE (16)) OPTIONAL,
            scs-30kHz [1] BIT STRING  (SIZE (16)) OPTIONAL,
            scs-60kHz [2] BIT STRING  (SIZE (16)) OPTIONAL
         },
         fr2 [1] SEQUENCE {
            scs-60kHz [0] BIT STRING  (SIZE (8)) OPTIONAL,
            scs-120kHz [1] BIT STRING  (SIZE (8)) OPTIONAL
         }
      } OPTIONAL
   ]],
   [[
      asymmetricBandwidthCombinationSet [21] BIT STRING  (SIZE (1..32)) OPTIONAL
   ]],
   [[
      sharedSpectrumChAccessParamsPerBand-r16 [22] 
         SharedSpectrumChAccessParamsPerBand-r16 OPTIONAL,
      cancelOverlappingPUSCH-r16 [23] ENUMERATED { supported(0) } OPTIONAL,
      multipleRateMatchingEUTRA-CRS-r16 [24] SEQUENCE {
         maxNumberPatterns-r16 [0] INTEGER (2..6),
         maxNumberNon-OverlapPatterns-r16 [1] INTEGER (1..3)
      } OPTIONAL,
      overlapRateMatchingEUTRA-CRS-r16 [25] ENUMERATED { supported(0) }
          OPTIONAL,
      pdsch-MappingTypeB-Alt-r16 [26] ENUMERATED { supported(0) } OPTIONAL,
      oneSlotPeriodicTRS-r16 [27] ENUMERATED { supported(0) } OPTIONAL,
      olpc-SRS-Pos-r16 [28] OLPC-SRS-Pos-r16 OPTIONAL,
      spatialRelationsSRS-Pos-r16 [29] SpatialRelationsSRS-Pos-r16 OPTIONAL,
      simulSRS-MIMO-TransWithinBand-r16 [30] ENUMERATED { n2(0) } OPTIONAL,
      channelBW-DL-IAB-r16 [31] EXPLICIT CHOICE {
         fr1-100mhz [0] SEQUENCE {
            scs-15kHz [0] ENUMERATED { supported(0) } OPTIONAL,
            scs-30kHz [1] ENUMERATED { supported(0) } OPTIONAL,
            scs-60kHz [2] ENUMERATED { supported(0) } OPTIONAL
         },
         fr2-200mhz [1] SEQUENCE {
            scs-60kHz [0] ENUMERATED { supported(0) } OPTIONAL,
            scs-120kHz [1] ENUMERATED { supported(0) } OPTIONAL
         }
      } OPTIONAL,
      channelBW-UL-IAB-r16 [32] EXPLICIT CHOICE {
         fr1-100mhz [0] SEQUENCE {
            scs-15kHz [0] ENUMERATED { supported(0) } OPTIONAL,
            scs-30kHz [1] ENUMERATED { supported(0) } OPTIONAL,
            scs-60kHz [2] ENUMERATED { supported(0) } OPTIONAL
         },
         fr2-200mhz [1] SEQUENCE {
            scs-60kHz [0] ENUMERATED { supported(0) } OPTIONAL,
            scs-120kHz [1] ENUMERATED { supported(0) } OPTIONAL
         }
      } OPTIONAL,
      rasterShift7dot5-IAB-r16 [33] ENUMERATED { supported(0) } OPTIONAL,
      ue-PowerClass-v1610 [34] ENUMERATED { pc1dot5(0) } OPTIONAL,
      condHandover-r16 [35] ENUMERATED { supported(0) } OPTIONAL,
      condHandoverFailure-r16 [36] ENUMERATED { supported(0) } OPTIONAL,
      condHandoverTwoTriggerEvents-r16 [37] ENUMERATED { supported(0) }
          OPTIONAL,
      condPSCellChange-r16 [38] ENUMERATED { supported(0) } OPTIONAL,
      condPSCellChangeTwoTriggerEvents-r16 [39] ENUMERATED { supported(0) }
          OPTIONAL,
      mpr-PowerBoost-FR2-r16 [40] ENUMERATED { supported(0) } OPTIONAL,
      activeConfiguredGrant-r16 [41] SEQUENCE {
         maxNumberConfigsPerBWP-r16 [0] ENUMERATED { n1(0), n2(1), n4(2), n8(3)
            , n12(4) },
         maxNumberConfigsAllCC-r16 [1] INTEGER (2..32)
      } OPTIONAL,
      jointReleaseConfiguredGrantType2-r16 [42] ENUMERATED { supported(0) }
          OPTIONAL,
      sps-r16 [43] SEQUENCE {
         maxNumberConfigsPerBWP-r16 [0] INTEGER (1..8),
         maxNumberConfigsAllCC-r16 [1] INTEGER (2..32)
      } OPTIONAL,
      jointReleaseSPS-r16 [44] ENUMERATED { supported(0) } OPTIONAL,
      simulSRS-TransWithinBand-r16 [45] ENUMERATED { n2(0) } OPTIONAL,
      trs-AdditionalBandwidth-r16 [46] ENUMERATED { trs-AddBW-Set1(0), 
         trs-AddBW-Set2(1) } OPTIONAL,
      handoverIntraF-IAB-r16 [47] ENUMERATED { supported(0) } OPTIONAL
   ]],
   [[
      simulTX-SRS-AntSwitchingIntraBandUL-CA-r16 [48] 
         SimulSRS-ForAntennaSwitching-r16 OPTIONAL,
      sharedSpectrumChAccessParamsPerBand-v1630 [49] 
         SharedSpectrumChAccessParamsPerBand-v1630 OPTIONAL
   ]],
   [[
      handoverUTRA-FDD-r16 [50] ENUMERATED { supported(0) } OPTIONAL,
      enhancedUL-TransientPeriod-r16 [51] ENUMERATED { us2(0), us4(1), us7(2) }
          OPTIONAL,
      sharedSpectrumChAccessParamsPerBand-v1640 [52] 
         SharedSpectrumChAccessParamsPerBand-v1640 OPTIONAL
   ]],
   [[
      type1-PUSCH-RepetitionMultiSlots-v1650 [53] ENUMERATED { supported(0) }
          OPTIONAL,
      type2-PUSCH-RepetitionMultiSlots-v1650 [54] ENUMERATED { supported(0) }
          OPTIONAL,
      pusch-RepetitionMultiSlots-v1650 [55] ENUMERATED { supported(0) }
          OPTIONAL,
      configuredUL-GrantType1-v1650 [56] ENUMERATED { supported(0) } OPTIONAL,
      configuredUL-GrantType2-v1650 [57] ENUMERATED { supported(0) } OPTIONAL,
      sharedSpectrumChAccessParamsPerBand-v1650 [58] 
         SharedSpectrumChAccessParamsPerBand-v1650 OPTIONAL
   ]],
   [[
      enhancedSkipUplinkTxConfigured-v1660 [59] ENUMERATED { supported(0) }
          OPTIONAL,
      enhancedSkipUplinkTxDynamic-v1660 [60] ENUMERATED { supported(0) }
          OPTIONAL
   ]],
   [[
      maxUplinkDutyCycle-PC1dot5-MPE-FR1-r16 [61] ENUMERATED { n10(0), n15(1), 
         n20(2), n25(3), n30(4), n40(5), n50(6), n60(7), n70(8), n80(9), 
         n90(10), n100(11) } OPTIONAL,
      txDiversity-r16 [62] ENUMERATED { supported(0) } OPTIONAL
   ]],
   [[
      pdsch-1024QAM-FR1-r17 [63] ENUMERATED { supported(0) } OPTIONAL,
      ue-PowerClass-v1700 [64] ENUMERATED { pc5(0), pc6(1), pc7(2) } OPTIONAL,
      fr2-2-AccessParamsPerBand-r17 [65] FR2-2-AccessParamsPerBand-r17 OPTIONAL
         ,
      rlm-Relaxation-r17 [66] ENUMERATED { supported(0) } OPTIONAL,
      bfd-Relaxation-r17 [67] ENUMERATED { supported(0) } OPTIONAL,
      cg-SDT-r17 [68] ENUMERATED { supported(0) } OPTIONAL,
      locationBasedCondHandover-r17 [69] ENUMERATED { supported(0) } OPTIONAL,
      timeBasedCondHandover-r17 [70] ENUMERATED { supported(0) } OPTIONAL,
      eventA4BasedCondHandover-r17 [71] ENUMERATED { supported(0) } OPTIONAL,
      mn-InitiatedCondPSCellChangeNRDC-r17 [72] ENUMERATED { supported(0) }
          OPTIONAL,
      sn-InitiatedCondPSCellChangeNRDC-r17 [73] ENUMERATED { supported(0) }
          OPTIONAL,
      pdcch-SkippingWithoutSSSG-r17 [74] ENUMERATED { supported(0) } OPTIONAL,
      sssg-Switching-1BitInd-r17 [75] ENUMERATED { supported(0) } OPTIONAL,
      sssg-Switching-2BitInd-r17 [76] ENUMERATED { supported(0) } OPTIONAL,
      pdcch-SkippingWithSSSG-r17 [77] ENUMERATED { supported(0) } OPTIONAL,
      searchSpaceSetGrp-switchCap2-r17 [78] ENUMERATED { supported(0) }
          OPTIONAL,
      uplinkPreCompensation-r17 [79] ENUMERATED { supported(0) } OPTIONAL,
      uplink-TA-Reporting-r17 [80] ENUMERATED { supported(0) } OPTIONAL,
      max-HARQ-ProcessNumber-r17 [81] ENUMERATED { u16d32(0), u32d16(1), 
         u32d32(2) } OPTIONAL,
      type2-HARQ-Codebook-r17 [82] ENUMERATED { supported(0) } OPTIONAL,
      type1-HARQ-Codebook-r17 [83] ENUMERATED { supported(0) } OPTIONAL,
      type3-HARQ-Codebook-r17 [84] ENUMERATED { supported(0) } OPTIONAL,
      ue-specific-K-Offset-r17 [85] ENUMERATED { supported(0) } OPTIONAL,
      multiPDSCH-SingleDCI-FR2-1-SCS-120kHz-r17 [86] ENUMERATED { supported(0)
          } OPTIONAL,
      multiPUSCH-SingleDCI-FR2-1-SCS-120kHz-r17 [87] ENUMERATED { supported(0)
          } OPTIONAL,
      parallelPRS-MeasRRC-Inactive-r17 [88] ENUMERATED { supported(0) }
          OPTIONAL,
      nr-UE-TxTEG-ID-MaxSupport-r17 [89] ENUMERATED { n1(0), n2(1), n3(2), 
         n4(3), n6(4), n8(5) } OPTIONAL,
      prs-ProcessingRRC-Inactive-r17 [90] ENUMERATED { supported(0) } OPTIONAL
         ,
      prs-ProcessingWindowType1A-r17 [91] ENUMERATED { option1(0), option2(1), 
         option3(2) } OPTIONAL,
      prs-ProcessingWindowType1B-r17 [92] ENUMERATED { option1(0), option2(1), 
         option3(2) } OPTIONAL,
      prs-ProcessingWindowType2-r17 [93] ENUMERATED { option1(0), option2(1), 
         option3(2) } OPTIONAL,
      srs-AllPosResourcesRRC-Inactive-r17 [94] 
         SRS-AllPosResourcesRRC-Inactive-r17 OPTIONAL,
      olpc-SRS-PosRRC-Inactive-r17 [95] OLPC-SRS-Pos-r16 OPTIONAL,
      spatialRelationsSRS-PosRRC-Inactive-r17 [96] SpatialRelationsSRS-Pos-r16
          OPTIONAL,
      maxNumberPUSCH-TypeA-Repetition-r17 [97] ENUMERATED { supported(0) }
          OPTIONAL,
      puschTypeA-RepetitionsAvailSlot-r17 [98] ENUMERATED { supported(0) }
          OPTIONAL,
      tb-ProcessingMultiSlotPUSCH-r17 [99] ENUMERATED { supported(0) } OPTIONAL
         ,
      tb-ProcessingRepMultiSlotPUSCH-r17 [100] ENUMERATED { supported(0) }
          OPTIONAL,
      maxDurationDMRS-Bundling-r17 [101] SEQUENCE {
         fdd-r17 [0] ENUMERATED { n4(0), n8(1), n16(2), n32(3) } OPTIONAL,
         tdd-r17 [1] ENUMERATED { n2(0), n4(1), n8(2), n16(3) } OPTIONAL
      } OPTIONAL,
      pusch-RepetitionMsg3-r17 [102] ENUMERATED { supported(0) } OPTIONAL,
      sharedSpectrumChAccessParamsPerBand-v1710 [103] 
         SharedSpectrumChAccessParamsPerBand-v1710 OPTIONAL,
      parallelMeasurementWithoutRestriction-r17 [104] ENUMERATED { supported(0)
          } OPTIONAL,
      maxNumber-NGSO-SatellitesWithinOneSMTC-r17 [105] ENUMERATED { n1(0), 
         n2(1), n3(2), n4(3) } OPTIONAL,
      k1-RangeExtension-r17 [106] ENUMERATED { supported(0) } OPTIONAL,
      aperiodicCSI-RS-FastScellActivation-r17 [107] SEQUENCE {
         maxNumberAperiodicCSI-RS-PerCC-r17 [0] ENUMERATED { n8(0), n16(1), 
            n32(2), n48(3), n64(4), n128(5), n255(6) },
         maxNumberAperiodicCSI-RS-AcrossCCs-r17 [1] ENUMERATED { n8(0), n16(1)
            , n32(2), n64(3), n128(4), n256(5), n512(6), n1024(7) }
      } OPTIONAL,
      aperiodicCSI-RS-AdditionalBandwidth-r17 [108] ENUMERATED { addBW-Set1(0)
         , addBW-Set2(1) } OPTIONAL,
      bwp-WithoutCD-SSB-OrNCD-SSB-RedCap-r17 [109] ENUMERATED { supported(0) }
          OPTIONAL,
      halfDuplexFDD-TypeA-RedCap-r17 [110] ENUMERATED { supported(0) } OPTIONAL
         ,
      posSRS-RRC-Inactive-OutsideInitialUL-BWP-r17 [111] 
         PosSRS-RRC-Inactive-OutsideInitialUL-BWP-r17 OPTIONAL,
      channelBWs-DL-SCS-480kHz-FR2-2-r17 [112] BIT STRING  (SIZE (8)) OPTIONAL,
      channelBWs-UL-SCS-480kHz-FR2-2-r17 [113] BIT STRING  (SIZE (8)) OPTIONAL,
      channelBWs-DL-SCS-960kHz-FR2-2-r17 [114] BIT STRING  (SIZE (8)) OPTIONAL,
      channelBWs-UL-SCS-960kHz-FR2-2-r17 [115] BIT STRING  (SIZE (8)) OPTIONAL,
      ul-GapFR2-r17 [116] ENUMERATED { supported(0) } OPTIONAL,
      oneShotHARQ-feedbackTriggeredByDCI-1-2-r17 [117] ENUMERATED { 
         supported(0) } OPTIONAL,
      oneShotHARQ-feedbackPhy-Priority-r17 [118] ENUMERATED { supported(0) }
          OPTIONAL,
      enhancedType3-HARQ-CodebookFeedback-r17 [119] SEQUENCE {
         enhancedType3-HARQ-Codebooks-r17 [0] ENUMERATED { n1(0), n2(1), n4(2)
            , n8(3) },
         maxNumberPUCCH-Transmissions-r17 [1] ENUMERATED { n1(0), n2(1), n3(2)
            , n4(3), n5(4), n6(5), n7(6) }
      } OPTIONAL,
      triggeredHARQ-CodebookRetx-r17 [120] SEQUENCE {
         minHARQ-Retx-Offset-r17 [0] ENUMERATED { n-7(0), n-5(1), n-3(2), 
            n-1(3), n1(4) },
         maxHARQ-Retx-Offset-r17 [1] ENUMERATED { n4(0), n6(1), n8(2), n10(3), 
            n12(4), n14(5), n16(6), n18(7), n20(8), n22(9), n24(10) }
      } OPTIONAL
   ]],
   [[
      ue-OneShotUL-TimingAdj-r17 [121] ENUMERATED { supported(0) } OPTIONAL,
      pucch-Repetition-F0-2-r17 [122] ENUMERATED { supported(0) } OPTIONAL,
      cqi-4-BitsSubbandNTN-SharedSpectrumChAccess-r17 [123] ENUMERATED { 
         supported(0) } OPTIONAL,
      mux-HARQ-ACK-DiffPriorities-r17 [124] ENUMERATED { supported(0) }
          OPTIONAL,
      ta-BasedPDC-NTN-SharedSpectrumChAccess-r17 [125] ENUMERATED { 
         supported(0) } OPTIONAL,
      ack-NACK-FeedbackForMulticastWithDCI-Enabler-r17 [126] ENUMERATED { 
         supported(0) } OPTIONAL,
      maxNumberG-RNTI-r17 [127] INTEGER (2..8) OPTIONAL,
      dynamicMulticastDCI-Format4-2-r17 [128] ENUMERATED { supported(0) }
          OPTIONAL,
      maxModulationOrderForMulticast-r17 [129] EXPLICIT CHOICE {
         fr1-r17 [0] ENUMERATED { qam256(0), qam1024(1) },
         fr2-r17 [1] ENUMERATED { qam64(0), qam256(1) }
      } OPTIONAL,
      dynamicSlotRepetitionMulticastTN-NonSharedSpectrumChAccess-r17 [130] 
         ENUMERATED { n8(0), n16(1) } OPTIONAL,
      dynamicSlotRepetitionMulticastNTN-SharedSpectrumChAccess-r17 [131] 
         ENUMERATED { n8(0), n16(1) } OPTIONAL,
      nack-OnlyFeedbackForMulticastWithDCI-Enabler-r17 [132] ENUMERATED { 
         supported(0) } OPTIONAL,
      ack-NACK-FeedbackForSPS-MulticastWithDCI-Enabler-r17 [133] ENUMERATED { 
         supported(0) } OPTIONAL,
      maxNumberG-CS-RNTI-r17 [134] INTEGER (2..8) OPTIONAL,
      re-LevelRateMatchingForMulticast-r17 [135] ENUMERATED { supported(0) }
          OPTIONAL,
      pdsch-1024QAM-2MIMO-FR1-r17 [136] ENUMERATED { supported(0) } OPTIONAL,
      prs-MeasurementWithoutMG-r17 [137] ENUMERATED { cpLength(0), 
         quarterSymbol(1), halfSymbol(2), halfSlot(3) } OPTIONAL,
      maxNumber-LEO-SatellitesPerCarrier-r17 [138] INTEGER (3..4) OPTIONAL,
      prs-ProcessingCapabilityOutsideMGinPPW-r17 [139] SEQUENCE (SIZE (1..3)) OF 
         PRS-ProcessingCapabilityOutsideMGinPPWperType-r17 OPTIONAL,
      srs-SemiPersistent-PosResourcesRRC-Inactive-r17 [140] SEQUENCE {
         maxNumOfSemiPersistentSRSposResources-r17 [0] ENUMERATED { n1(0), 
            n2(1), n4(2), n8(3), n16(4), n32(5), n64(6) },
         maxNumOfSemiPersistentSRSposResourcesPerSlot-r17 [1] ENUMERATED { 
            n1(0), n2(1), n3(2), n4(3), n5(4), n6(5), n8(6), n10(7), n12(8), 
            n14(9) }
      } OPTIONAL,
      channelBWs-DL-SCS-120kHz-FR2-2-r17 [141] BIT STRING  (SIZE (8)) OPTIONAL,
      channelBWs-UL-SCS-120kHz-FR2-2-r17 [142] BIT STRING  (SIZE (8)) OPTIONAL
   ]],
   [[
      dmrs-BundlingPUSCH-RepTypeA-r17 [143] ENUMERATED { supported(0) }
          OPTIONAL,
      dmrs-BundlingPUSCH-RepTypeB-r17 [144] ENUMERATED { supported(0) }
          OPTIONAL,
      dmrs-BundlingPUSCH-multiSlot-r17 [145] ENUMERATED { supported(0) }
          OPTIONAL,
      dmrs-BundlingPUCCH-Rep-r17 [146] ENUMERATED { supported(0) } OPTIONAL,
      interSlotFreqHopInterSlotBundlingPUSCH-r17 [147] ENUMERATED { 
         supported(0) } OPTIONAL,
      interSlotFreqHopPUCCH-r17 [148] ENUMERATED { supported(0) } OPTIONAL,
      dmrs-BundlingRestart-r17 [149] ENUMERATED { supported(0) } OPTIONAL,
      dmrs-BundlingNonBackToBackTX-r17 [150] ENUMERATED { supported(0) }
          OPTIONAL
   ]],
   [[
      maxDynamicSlotRepetitionForSPS-Multicast-r17 [151] ENUMERATED { n8(0), 
         n16(1) } OPTIONAL,
      nack-OnlyFeedbackForSPS-MulticastWithDCI-Enabler-r17 [152] ENUMERATED { 
         supported(0) } OPTIONAL,
      sps-MulticastDCI-Format4-2-r17 [153] ENUMERATED { supported(0) } OPTIONAL
         ,
      sps-MulticastMultiConfig-r17 [154] INTEGER (1..8) OPTIONAL,
      priorityIndicatorInDCI-Multicast-r17 [155] ENUMERATED { supported(0) }
          OPTIONAL,
      priorityIndicatorInDCI-SPS-Multicast-r17 [156] ENUMERATED { supported(0)
          } OPTIONAL,
      twoHARQ-ACK-CodebookForUnicastAndMulticast-r17 [157] ENUMERATED { 
         supported(0) } OPTIONAL,
      multiPUCCH-HARQ-ACK-ForMulticastUnicast-r17 [158] ENUMERATED { 
         supported(0) } OPTIONAL,
      releaseSPS-MulticastWithCS-RNTI-r17 [159] ENUMERATED { supported(0) }
          OPTIONAL
   ]]
}

-- TAG-REDCAPPARAMETERS-STOP
-- TAG-RF-PARAMETERS-START
RF-Parameters ::= SEQUENCE {
   supportedBandListNR [0] SEQUENCE (SIZE (1..maxBands)) OF BandNR,
   supportedBandCombinationList [1] BandCombinationList OPTIONAL,
   appliedFreqBandListFilter [2] FreqBandList OPTIONAL,
   ...,
   [[
      supportedBandCombinationList-v1540 [3] BandCombinationList-v1540 OPTIONAL
         ,
      srs-SwitchingTimeRequested [4] ENUMERATED { true(0) } OPTIONAL
   ]],
   [[
      supportedBandCombinationList-v1550 [5] BandCombinationList-v1550 OPTIONAL
   ]],
   [[
      supportedBandCombinationList-v1560 [6] BandCombinationList-v1560 OPTIONAL
   ]],
   [[
      supportedBandCombinationList-v1610 [7] BandCombinationList-v1610 OPTIONAL
         ,
      supportedBandCombinationListSidelinkEUTRA-NR-r16 [8] 
         BandCombinationListSidelinkEUTRA-NR-r16 OPTIONAL,
      supportedBandCombinationList-UplinkTxSwitch-r16 [9] 
         BandCombinationList-UplinkTxSwitch-r16 OPTIONAL
   ]],
   [[
      supportedBandCombinationList-v1630 [10] BandCombinationList-v1630
          OPTIONAL,
      supportedBandCombinationListSidelinkEUTRA-NR-v1630 [11] 
         BandCombinationListSidelinkEUTRA-NR-v1630 OPTIONAL,
      supportedBandCombinationList-UplinkTxSwitch-v1630 [12] 
         BandCombinationList-UplinkTxSwitch-v1630 OPTIONAL
   ]],
   [[
      supportedBandCombinationList-v1640 [13] BandCombinationList-v1640
          OPTIONAL,
      supportedBandCombinationList-UplinkTxSwitch-v1640 [14] 
         BandCombinationList-UplinkTxSwitch-v1640 OPTIONAL
   ]],
   [[
      supportedBandCombinationList-v1650 [15] BandCombinationList-v1650
          OPTIONAL,
      supportedBandCombinationList-UplinkTxSwitch-v1650 [16] 
         BandCombinationList-UplinkTxSwitch-v1650 OPTIONAL
   ]],
   [[
      extendedBand-n77-r16 [17] ENUMERATED { supported(0) } OPTIONAL
   ]],
   [[
      supportedBandCombinationList-UplinkTxSwitch-v1670 [18] 
         BandCombinationList-UplinkTxSwitch-v1670 OPTIONAL
   ]],
   [[
      supportedBandCombinationList-v1680 [19] BandCombinationList-v1680
          OPTIONAL
   ]],
   [[
      supportedBandCombinationList-v1690 [20] BandCombinationList-v1690
          OPTIONAL,
      supportedBandCombinationList-UplinkTxSwitch-v1690 [21] 
         BandCombinationList-UplinkTxSwitch-v1690 OPTIONAL
   ]],
   [[
      supportedBandCombinationList-v1700 [22] BandCombinationList-v1700
          OPTIONAL,
      supportedBandCombinationList-UplinkTxSwitch-v1700 [23] 
         BandCombinationList-UplinkTxSwitch-v1700 OPTIONAL,
      supportedBandCombinationListSL-RelayDiscovery-r17 [24] OCTET STRING
          OPTIONAL,
      supportedBandCombinationListSL-NonRelayDiscovery-r17 [25] OCTET STRING
          OPTIONAL,
      supportedBandCombinationListSidelinkEUTRA-NR-v1710 [26] 
         BandCombinationListSidelinkEUTRA-NR-v1710 OPTIONAL,
      sidelinkRequested-r17 [27] ENUMERATED { true(0) } OPTIONAL,
      extendedBand-n77-2-r17 [28] ENUMERATED { supported(0) } OPTIONAL
   ]],
   [[
      supportedBandCombinationList-v1720 [29] BandCombinationList-v1720
          OPTIONAL,
      supportedBandCombinationList-UplinkTxSwitch-v1720 [30] 
         BandCombinationList-UplinkTxSwitch-v1720 OPTIONAL
   ]],
   [[
      supportedBandCombinationList-v1730 [31] BandCombinationList-v1730
          OPTIONAL,
      supportedBandCombinationList-UplinkTxSwitch-v1730 [32] 
         BandCombinationList-UplinkTxSwitch-v1730 OPTIONAL,
      supportedBandCombinationListSL-RelayDiscovery-v1730 [33] 
         BandCombinationListSL-Discovery-r17 OPTIONAL,
      supportedBandCombinationListSL-NonRelayDiscovery-v1730 [34] 
         BandCombinationListSL-Discovery-r17 OPTIONAL
   ]],
   [[
      supportedBandCombinationList-v1740 [35] BandCombinationList-v1740
          OPTIONAL,
      supportedBandCombinationList-UplinkTxSwitch-v1740 [36] 
         BandCombinationList-UplinkTxSwitch-v1740 OPTIONAL
   ]],
   [[
      supportedBandCombinationList-v1760 [37] BandCombinationList-v1760
          OPTIONAL,
      supportedBandCombinationList-UplinkTxSwitch-v1760 [38] 
         BandCombinationList-UplinkTxSwitch-v1760 OPTIONAL
   ]],
   [[
      dummy1 [39] BandCombinationList-v1770 OPTIONAL,
      dummy2 [40] BandCombinationList-UplinkTxSwitch-v1770 OPTIONAL
   ]],
   [[
      supportedBandCombinationList-v1780 [41] BandCombinationList-v1780
          OPTIONAL,
      supportedBandCombinationList-UplinkTxSwitch-v1780 [42] 
         BandCombinationList-UplinkTxSwitch-v1780 OPTIONAL
   ]]
}

RF-Parameters-v15g0 ::= SEQUENCE {
   supportedBandCombinationList-v15g0 [0] BandCombinationList-v15g0 OPTIONAL
}

RF-Parameters-v16a0 ::= SEQUENCE {
   supportedBandCombinationList-v16a0 [0] BandCombinationList-v16a0 OPTIONAL,
   supportedBandCombinationList-UplinkTxSwitch-v16a0 [1] 
      BandCombinationList-UplinkTxSwitch-v16a0 OPTIONAL
}

BandNR-v16c0 ::= SEQUENCE {
   pusch-RepetitionTypeA-v16c0 [0] ENUMERATED { supported(0) } OPTIONAL,
   ...
}

RF-Parameters-v16c0 ::= SEQUENCE {
   supportedBandListNR-v16c0 [0] SEQUENCE (SIZE (1..maxBands)) OF BandNR-v16c0
}

-- TAG-RF-PARAMETERS-STOP
-- TAG-RF-PARAMETERSMRDC-START
RF-ParametersMRDC ::= SEQUENCE {
   supportedBandCombinationList [0] BandCombinationList OPTIONAL,
   appliedFreqBandListFilter [1] FreqBandList OPTIONAL,
   ...,
   [[
      srs-SwitchingTimeRequested [2] ENUMERATED { true(0) } OPTIONAL,
      supportedBandCombinationList-v1540 [3] BandCombinationList-v1540 OPTIONAL
   ]],
   [[
      supportedBandCombinationList-v1550 [4] BandCombinationList-v1550 OPTIONAL
   ]],
   [[
      supportedBandCombinationList-v1560 [5] BandCombinationList-v1560 OPTIONAL
         ,
      supportedBandCombinationListNEDC-Only [6] BandCombinationList OPTIONAL
   ]],
   [[
      supportedBandCombinationList-v1570 [7] BandCombinationList-v1570 OPTIONAL
   ]],
   [[
      supportedBandCombinationList-v1580 [8] BandCombinationList-v1580 OPTIONAL
   ]],
   [[
      supportedBandCombinationList-v1590 [9] BandCombinationList-v1590 OPTIONAL
   ]],
   [[
      supportedBandCombinationListNEDC-Only-v15a0 [10] SEQUENCE {
         supportedBandCombinationList-v1540 [0] BandCombinationList-v1540
             OPTIONAL,
         supportedBandCombinationList-v1560 [1] BandCombinationList-v1560
             OPTIONAL,
         supportedBandCombinationList-v1570 [2] BandCombinationList-v1570
             OPTIONAL,
         supportedBandCombinationList-v1580 [3] BandCombinationList-v1580
             OPTIONAL,
         supportedBandCombinationList-v1590 [4] BandCombinationList-v1590
             OPTIONAL
      } OPTIONAL
   ]],
   [[
      supportedBandCombinationList-v1610 [11] BandCombinationList-v1610
          OPTIONAL,
      supportedBandCombinationListNEDC-Only-v1610 [12] 
         BandCombinationList-v1610 OPTIONAL,
      supportedBandCombinationList-UplinkTxSwitch-r16 [13] 
         BandCombinationList-UplinkTxSwitch-r16 OPTIONAL
   ]],
   [[
      supportedBandCombinationList-v1630 [14] BandCombinationList-v1630
          OPTIONAL,
      supportedBandCombinationListNEDC-Only-v1630 [15] 
         BandCombinationList-v1630 OPTIONAL,
      supportedBandCombinationList-UplinkTxSwitch-v1630 [16] 
         BandCombinationList-UplinkTxSwitch-v1630 OPTIONAL
   ]],
   [[
      supportedBandCombinationList-v1640 [17] BandCombinationList-v1640
          OPTIONAL,
      supportedBandCombinationListNEDC-Only-v1640 [18] 
         BandCombinationList-v1640 OPTIONAL,
      supportedBandCombinationList-UplinkTxSwitch-v1640 [19] 
         BandCombinationList-UplinkTxSwitch-v1640 OPTIONAL
   ]],
   [[
      supportedBandCombinationList-UplinkTxSwitch-v1670 [20] 
         BandCombinationList-UplinkTxSwitch-v1670 OPTIONAL
   ]],
   [[
      supportedBandCombinationList-v1700 [21] BandCombinationList-v1700
          OPTIONAL,
      supportedBandCombinationList-UplinkTxSwitch-v1700 [22] 
         BandCombinationList-UplinkTxSwitch-v1700 OPTIONAL
   ]],
   [[
      supportedBandCombinationList-v1720 [23] BandCombinationList-v1720
          OPTIONAL,
      supportedBandCombinationListNEDC-Only-v1720 [24] SEQUENCE {
         supportedBandCombinationList-v1700 [0] BandCombinationList-v1700
             OPTIONAL,
         supportedBandCombinationList-v1720 [1] BandCombinationList-v1720
             OPTIONAL
      } OPTIONAL,
      supportedBandCombinationList-UplinkTxSwitch-v1720 [25] 
         BandCombinationList-UplinkTxSwitch-v1720 OPTIONAL
   ]],
   [[
      supportedBandCombinationList-v1730 [26] BandCombinationList-v1730
          OPTIONAL,
      supportedBandCombinationListNEDC-Only-v1730 [27] 
         BandCombinationList-v1730 OPTIONAL,
      supportedBandCombinationList-UplinkTxSwitch-v1730 [28] 
         BandCombinationList-UplinkTxSwitch-v1730 OPTIONAL
   ]],
   [[
      supportedBandCombinationList-v1740 [29] BandCombinationList-v1740
          OPTIONAL,
      supportedBandCombinationListNEDC-Only-v1740 [30] 
         BandCombinationList-v1740 OPTIONAL,
      supportedBandCombinationList-UplinkTxSwitch-v1740 [31] 
         BandCombinationList-UplinkTxSwitch-v1740 OPTIONAL
   ]],
   [[
      dummy1 [32] BandCombinationList-v1770 OPTIONAL,
      dummy2 [33] BandCombinationList-UplinkTxSwitch-v1770 OPTIONAL
   ]],
   [[
      supportedBandCombinationList-v1780 [34] BandCombinationList-v1780
          OPTIONAL,
      supportedBandCombinationListNEDC-Only-v1780 [35] 
         BandCombinationList-v1780 OPTIONAL,
      supportedBandCombinationList-UplinkTxSwitch-v1780 [36] 
         BandCombinationList-UplinkTxSwitch-v1780 OPTIONAL
   ]]
}

RF-ParametersMRDC-v15g0 ::= SEQUENCE {
   supportedBandCombinationList-v15g0 [0] BandCombinationList-v15g0 OPTIONAL,
   supportedBandCombinationListNEDC-Only-v15g0 [1] BandCombinationList-v15g0
       OPTIONAL
}

RF-ParametersMRDC-v15n0 ::= SEQUENCE {
   supportedBandCombinationList-v15n0 [0] BandCombinationList-v15n0 OPTIONAL
}

RF-ParametersMRDC-v16e0 ::= SEQUENCE {
   supportedBandCombinationList-UplinkTxSwitch-v16e0 [0] 
      BandCombinationList-UplinkTxSwitch-v16e0 OPTIONAL
}

-- TAG-RF-PARAMETERSMRDC-STOP
-- TAG-RLC-PARAMETERS-START
RLC-Parameters ::= SEQUENCE {
   am-WithShortSN [0] ENUMERATED { supported(0) } OPTIONAL,
   um-WithShortSN [1] ENUMERATED { supported(0) } OPTIONAL,
   um-WithLongSN [2] ENUMERATED { supported(0) } OPTIONAL,
   ...,
   [[
      extendedT-PollRetransmit-r16 [3] ENUMERATED { supported(0) } OPTIONAL,
      extendedT-StatusProhibit-r16 [4] ENUMERATED { supported(0) } OPTIONAL
   ]],
   [[
      am-WithLongSN-RedCap-r17 [5] ENUMERATED { supported(0) } OPTIONAL
   ]]
}

-- TAG-RLC-PARAMETERS-STOP
-- TAG-SDAP-PARAMETERS-START
SDAP-Parameters ::= SEQUENCE {
   as-ReflectiveQoS [0] ENUMERATED { true(0) } OPTIONAL,
   ...,
   [[
      sdap-QOS-IAB-r16 [1] ENUMERATED { supported(0) } OPTIONAL,
      sdapHeaderIAB-r16 [2] ENUMERATED { supported(0) } OPTIONAL
   ]]
}

RLC-ParametersSidelink-r16 ::= SEQUENCE {
   am-WithLongSN-Sidelink-r16 [0] ENUMERATED { supported(0) } OPTIONAL,
   um-WithLongSN-Sidelink-r16 [1] ENUMERATED { supported(0) } OPTIONAL,
   ...
}

MAC-ParametersSidelinkCommon-r16 ::= SEQUENCE {
   lcp-RestrictionSidelink-r16 [0] ENUMERATED { supported(0) } OPTIONAL,
   multipleConfiguredGrantsSidelink-r16 [1] ENUMERATED { supported(0) }
       OPTIONAL,
   ...,
   [[
      drx-OnSidelink-r17 [2] ENUMERATED { supported(0) } OPTIONAL
   ]]
}

MAC-ParametersSidelinkXDD-Diff-r16 ::= SEQUENCE {
   multipleSR-ConfigurationsSidelink-r16 [0] ENUMERATED { supported(0) }
       OPTIONAL,
   logicalChannelSR-DelayTimerSidelink-r16 [1] ENUMERATED { supported(0) }
       OPTIONAL,
   ...
}

MAC-ParametersSidelink-r16 ::= SEQUENCE {
   mac-ParametersSidelinkCommon-r16 [0] MAC-ParametersSidelinkCommon-r16
       OPTIONAL,
   mac-ParametersSidelinkXDD-Diff-r16 [1] MAC-ParametersSidelinkXDD-Diff-r16
       OPTIONAL,
   ...
}

UE-SidelinkCapabilityAddXDD-Mode-r16 ::= SEQUENCE {
   mac-ParametersSidelinkXDD-Diff-r16 [0] MAC-ParametersSidelinkXDD-Diff-r16
       OPTIONAL
}

BandSidelink-r16 ::= SEQUENCE {
   freqBandSidelink-r16 [0] FreqBandIndicatorNR,
     --15-1
   sl-Reception-r16 [1] SEQUENCE {
      harq-RxProcessSidelink-r16 [0] ENUMERATED { n16(0), n24(1), n32(2), 
         n48(3), n64(4) },
      pscch-RxSidelink-r16 [1] ENUMERATED { value1(0), value2(1) },
      scs-CP-PatternRxSidelink-r16 [2] EXPLICIT CHOICE {
         fr1-r16 [0] SEQUENCE {
            scs-15kHz-r16 [0] BIT STRING  (SIZE (16)) OPTIONAL,
            scs-30kHz-r16 [1] BIT STRING  (SIZE (16)) OPTIONAL,
            scs-60kHz-r16 [2] BIT STRING  (SIZE (16)) OPTIONAL
         },
         fr2-r16 [1] SEQUENCE {
            scs-60kHz-r16 [0] BIT STRING  (SIZE (16)) OPTIONAL,
            scs-120kHz-r16 [1] BIT STRING  (SIZE (16)) OPTIONAL
         }
      } OPTIONAL,
      extendedCP-RxSidelink-r16 [3] ENUMERATED { supported(0) } OPTIONAL
   } OPTIONAL,
     --15-2
   sl-TransmissionMode1-r16 [2] SEQUENCE {
      harq-TxProcessModeOneSidelink-r16 [0] ENUMERATED { n8(0), n16(1) },
      scs-CP-PatternTxSidelinkModeOne-r16 [1] EXPLICIT CHOICE {
         fr1-r16 [0] SEQUENCE {
            scs-15kHz-r16 [0] BIT STRING  (SIZE (16)) OPTIONAL,
            scs-30kHz-r16 [1] BIT STRING  (SIZE (16)) OPTIONAL,
            scs-60kHz-r16 [2] BIT STRING  (SIZE (16)) OPTIONAL
         },
         fr2-r16 [1] SEQUENCE {
            scs-60kHz-r16 [0] BIT STRING  (SIZE (16)) OPTIONAL,
            scs-120kHz-r16 [1] BIT STRING  (SIZE (16)) OPTIONAL
         }
      },
      extendedCP-TxSidelink-r16 [2] ENUMERATED { supported(0) } OPTIONAL,
      harq-ReportOnPUCCH-r16 [3] ENUMERATED { supported(0) } OPTIONAL
   } OPTIONAL,
     --15-4
   sync-Sidelink-r16 [3] SEQUENCE {
      gNB-Sync-r16 [0] ENUMERATED { supported(0) } OPTIONAL,
      gNB-GNSS-UE-SyncWithPriorityOnGNB-ENB-r16 [1] ENUMERATED { supported(0) }
          OPTIONAL,
      gNB-GNSS-UE-SyncWithPriorityOnGNSS-r16 [2] ENUMERATED { supported(0) }
          OPTIONAL
   } OPTIONAL,
     --15-10
   sl-Tx-256QAM-r16 [4] ENUMERATED { supported(0) } OPTIONAL,
     --15-11
   psfch-FormatZeroSidelink-r16 [5] SEQUENCE {
      psfch-RxNumber [0] ENUMERATED { n5(0), n15(1), n25(2), n32(3), n35(4), 
         n45(5), n50(6), n64(7) },
      psfch-TxNumber [1] ENUMERATED { n4(0), n8(1), n16(2) }
   } OPTIONAL,
     --15-12
   lowSE-64QAM-MCS-TableSidelink-r16 [6] ENUMERATED { supported(0) } OPTIONAL,
     --15-15
   enb-sync-Sidelink-r16 [7] ENUMERATED { supported(0) } OPTIONAL,
   ...,
   [[
      sl-TransmissionMode2-r16 [8] SEQUENCE {
         harq-TxProcessModeTwoSidelink-r16 [0] ENUMERATED { n8(0), n16(1) },
         scs-CP-PatternTxSidelinkModeTwo-r16 [1] ENUMERATED { supported(0) }
             OPTIONAL,
         dl-openLoopPC-Sidelink-r16 [2] ENUMERATED { supported(0) } OPTIONAL
      } OPTIONAL,
      congestionControlSidelink-r16 [9] SEQUENCE {
         cbr-ReportSidelink-r16 [0] ENUMERATED { supported(0) } OPTIONAL,
         cbr-CR-TimeLimitSidelink-r16 [1] ENUMERATED { time1(0), time2(1) }
      } OPTIONAL,
      fewerSymbolSlotSidelink-r16 [10] ENUMERATED { supported(0) } OPTIONAL,
      sl-openLoopPC-RSRP-ReportSidelink-r16 [11] ENUMERATED { supported(0) }
          OPTIONAL,
      sl-Rx-256QAM-r16 [12] ENUMERATED { supported(0) } OPTIONAL
   ]],
   [[
      ue-PowerClassSidelink-r16 [13] ENUMERATED { pc2(0), pc3(1), spare6(2), 
         spare5(3), spare4(4), spare3(5), spare2(6), spare1(7) } OPTIONAL
   ]],
   [[
      sl-TransmissionMode2-RandomResourceSelection-r17 [14] SEQUENCE {
         harq-TxProcessModeTwoSidelink-r17 [0] ENUMERATED { n8(0), n16(1) },
         scs-CP-PatternTxSidelinkModeTwo-r17 [1] EXPLICIT CHOICE {
            fr1-r17 [0] SEQUENCE {
               scs-15kHz-r17 [0] BIT STRING  (SIZE (16)) OPTIONAL,
               scs-30kHz-r17 [1] BIT STRING  (SIZE (16)) OPTIONAL,
               scs-60kHz-r17 [2] BIT STRING  (SIZE (16)) OPTIONAL
            },
            fr2-r17 [1] SEQUENCE {
               scs-60kHz-r17 [0] BIT STRING  (SIZE (16)) OPTIONAL,
               scs-120kHz-r17 [1] BIT STRING  (SIZE (16)) OPTIONAL
            }
         } OPTIONAL,
         extendedCP-Mode2Random-r17 [2] ENUMERATED { supported(0) } OPTIONAL,
         dl-openLoopPC-Sidelink-r17 [3] ENUMERATED { supported(0) } OPTIONAL
      } OPTIONAL,
      sync-Sidelink-v1710 [15] SEQUENCE {
         sync-GNSS-r17 [0] ENUMERATED { supported(0) } OPTIONAL,
         gNB-Sync-r17 [1] ENUMERATED { supported(0) } OPTIONAL,
         gNB-GNSS-UE-SyncWithPriorityOnGNB-ENB-r17 [2] ENUMERATED { 
            supported(0) } OPTIONAL,
         gNB-GNSS-UE-SyncWithPriorityOnGNSS-r17 [3] ENUMERATED { supported(0) }
             OPTIONAL
      } OPTIONAL,
      enb-sync-Sidelink-v1710 [16] ENUMERATED { supported(0) } OPTIONAL,
      rx-IUC-Scheme1-PreferredMode2Sidelink-r17 [17] ENUMERATED { supported(0)
          } OPTIONAL,
      rx-IUC-Scheme1-NonPreferredMode2Sidelink-r17 [18] ENUMERATED { 
         supported(0) } OPTIONAL,
      rx-IUC-Scheme2-Mode2Sidelink-r17 [19] ENUMERATED { n5(0), n15(1), n25(2)
         , n32(3), n35(4), n45(5), n50(6), n64(7) } OPTIONAL,
      rx-IUC-Scheme1-SCI-r17 [20] ENUMERATED { supported(0) } OPTIONAL,
      rx-IUC-Scheme1-SCI-ExplicitReq-r17 [21] ENUMERATED { supported(0) }
          OPTIONAL
   ]]
}

RelayParameters-r17 ::= SEQUENCE {
   relayUE-Operation-L2-r17 [0] ENUMERATED { supported(0) } OPTIONAL,
   remoteUE-Operation-L2-r17 [1] ENUMERATED { supported(0) } OPTIONAL,
   remoteUE-PathSwitchToIdleInactiveRelay-r17 [2] ENUMERATED { supported(0) }
       OPTIONAL,
   ...
}

SidelinkParametersNR-r16 ::= SEQUENCE {
   rlc-ParametersSidelink-r16 [0] RLC-ParametersSidelink-r16 OPTIONAL,
   mac-ParametersSidelink-r16 [1] MAC-ParametersSidelink-r16 OPTIONAL,
   fdd-Add-UE-Sidelink-Capabilities-r16 [2] 
      UE-SidelinkCapabilityAddXDD-Mode-r16 OPTIONAL,
   tdd-Add-UE-Sidelink-Capabilities-r16 [3] 
      UE-SidelinkCapabilityAddXDD-Mode-r16 OPTIONAL,
   supportedBandListSidelink-r16 [4] SEQUENCE (SIZE (1..maxBands)) OF BandSidelink-r16
       OPTIONAL,
   ...,
   [[
      relayParameters-r17 [5] RelayParameters-r17 OPTIONAL
   ]],
   [[
      p0-OLPC-Sidelink-r17 [6] ENUMERATED { supported(0) } OPTIONAL
   ]]
}

BandSidelinkEUTRA-r16 ::= SEQUENCE {
   freqBandSidelinkEUTRA-r16 [0] FreqBandIndicatorEUTRA,
     -- R1 15-7: Transmitting LTE sidelink mode 3 scheduled by NR Uu
   gnb-ScheduledMode3SidelinkEUTRA-r16 [1] SEQUENCE {
      gnb-ScheduledMode3DelaySidelinkEUTRA-r16 [0] ENUMERATED { ms0(0), 
         ms0dot25(1), ms0dot5(2), ms0dot625(3), ms0dot75(4), ms1(5), 
         ms1dot25(6), ms1dot5(7), ms1dot75(8), ms2(9), ms2dot5(10), ms3(11), 
         ms4(12), ms5(13), ms6(14), ms8(15), ms10(16), ms20(17) }
   } OPTIONAL,
     -- R1 15-9: Transmitting LTE sidelink mode 4 configured by NR Uu
   gnb-ScheduledMode4SidelinkEUTRA-r16 [2] ENUMERATED { supported(0) } OPTIONAL
}

SidelinkParametersEUTRA-r16 ::= SEQUENCE {
   sl-ParametersEUTRA1-r16 [0] OCTET STRING OPTIONAL,
   sl-ParametersEUTRA2-r16 [1] OCTET STRING OPTIONAL,
   sl-ParametersEUTRA3-r16 [2] OCTET STRING OPTIONAL,
   supportedBandListSidelinkEUTRA-r16 [3] SEQUENCE (SIZE (1..maxBandsEUTRA)) OF 
      BandSidelinkEUTRA-r16 OPTIONAL,
   ...
}

-- TAG-SDAP-PARAMETERS-STOP
-- TAG-SIDELINKPARAMETERS-START
SidelinkParameters-r16 ::= SEQUENCE {
   sidelinkParametersNR-r16 [0] SidelinkParametersNR-r16 OPTIONAL,
   sidelinkParametersEUTRA-r16 [1] SidelinkParametersEUTRA-r16 OPTIONAL
}

UE-CapabilityRequestFilterNR-v1710 ::= SEQUENCE {
   sidelinkRequest-r17 [0] ENUMERATED { true(0) } OPTIONAL, -- Need N
   nonCriticalExtension [1] SEQUENCE {

   } OPTIONAL
}

UE-CapabilityRequestFilterNR-v1540 ::= SEQUENCE {
   srs-SwitchingTimeRequest [0] ENUMERATED { true(0) } OPTIONAL, -- Need N
   nonCriticalExtension [1] UE-CapabilityRequestFilterNR-v1710 OPTIONAL
}

-- TAG-UE-CAPABILITYREQUESTFILTERCOMMON-STOP
-- TAG-UE-CAPABILITYREQUESTFILTERNR-START
UE-CapabilityRequestFilterNR ::= SEQUENCE {
   frequencyBandListFilter [0] FreqBandList OPTIONAL, -- Need N
   nonCriticalExtension [1] UE-CapabilityRequestFilterNR-v1540 OPTIONAL
}

UE-MRDC-Capability-v16e0 ::= SEQUENCE {
   rf-ParametersMRDC-v16e0 [0] RF-ParametersMRDC-v16e0 OPTIONAL,
   nonCriticalExtension [1] SEQUENCE {

   } OPTIONAL
}

UE-MRDC-Capability-v15n0 ::= SEQUENCE {
   rf-ParametersMRDC-v15n0 [0] RF-ParametersMRDC-v15n0 OPTIONAL,
 -- Following field is only for REL-15 late non-critical extensions
   lateNonCriticalExtension [1] OCTET STRING OPTIONAL,
   nonCriticalExtension [2] UE-MRDC-Capability-v16e0 OPTIONAL
}

-- Late non-critical extensions:
UE-MRDC-Capability-v15g0 ::= SEQUENCE {
   rf-ParametersMRDC-v15g0 [0] RF-ParametersMRDC-v15g0 OPTIONAL,
   nonCriticalExtension [1] UE-MRDC-Capability-v15n0 OPTIONAL
}

UE-MRDC-CapabilityAddXDD-Mode-v1560 ::= SEQUENCE {
   measAndMobParametersMRDC-XDD-Diff-v1560 [0] 
      MeasAndMobParametersMRDC-XDD-Diff-v1560 OPTIONAL
}

GeneralParametersMRDC-v1610 ::= SEQUENCE {
   f1c-OverEUTRA-r16 [0] ENUMERATED { supported(0) } OPTIONAL
}

UE-MRDC-Capability-v1730 ::= SEQUENCE {
   measAndMobParametersMRDC-v1730 [0] MeasAndMobParametersMRDC-v1730 OPTIONAL,
   nonCriticalExtension [1] SEQUENCE {

   } OPTIONAL
}

UE-MRDC-Capability-v1700 ::= SEQUENCE {
   measAndMobParametersMRDC-v1700 [0] MeasAndMobParametersMRDC-v1700,
   nonCriticalExtension [1] UE-MRDC-Capability-v1730 OPTIONAL
}

UE-MRDC-Capability-v1610 ::= SEQUENCE {
   measAndMobParametersMRDC-v1610 [0] MeasAndMobParametersMRDC-v1610 OPTIONAL,
   generalParametersMRDC-v1610 [1] GeneralParametersMRDC-v1610 OPTIONAL,
   pdcp-ParametersMRDC-v1610 [2] PDCP-ParametersMRDC-v1610 OPTIONAL,
   nonCriticalExtension [3] UE-MRDC-Capability-v1700 OPTIONAL
}

-- Regular non-critical extensions:
UE-MRDC-Capability-v1560 ::= SEQUENCE {
   receivedFilters [0] OCTET STRING (CONTAINING UECapabilityEnquiry-v1560-IEs)
       OPTIONAL,
   measAndMobParametersMRDC-v1560 [1] MeasAndMobParametersMRDC-v1560 OPTIONAL,
   fdd-Add-UE-MRDC-Capabilities-v1560 [2] UE-MRDC-CapabilityAddXDD-Mode-v1560
       OPTIONAL,
   tdd-Add-UE-MRDC-Capabilities-v1560 [3] UE-MRDC-CapabilityAddXDD-Mode-v1560
       OPTIONAL,
   nonCriticalExtension [4] UE-MRDC-Capability-v1610 OPTIONAL
}

-- TAG-UE-CAPABILITYREQUESTFILTERNR-STOP
-- TAG-UE-MRDC-CAPABILITY-START
UE-MRDC-Capability ::= SEQUENCE {
   measAndMobParametersMRDC [0] MeasAndMobParametersMRDC OPTIONAL,
   phy-ParametersMRDC-v1530 [1] Phy-ParametersMRDC OPTIONAL,
   rf-ParametersMRDC [2] RF-ParametersMRDC,
   generalParametersMRDC [3] GeneralParametersMRDC-XDD-Diff OPTIONAL,
   fdd-Add-UE-MRDC-Capabilities [4] UE-MRDC-CapabilityAddXDD-Mode OPTIONAL,
   tdd-Add-UE-MRDC-Capabilities [5] UE-MRDC-CapabilityAddXDD-Mode OPTIONAL,
   fr1-Add-UE-MRDC-Capabilities [6] UE-MRDC-CapabilityAddFRX-Mode OPTIONAL,
   fr2-Add-UE-MRDC-Capabilities [7] UE-MRDC-CapabilityAddFRX-Mode OPTIONAL,
   featureSetCombinations [8] SEQUENCE (SIZE (1..maxFeatureSetCombinations)) OF FeatureSetCombination
       OPTIONAL,
   pdcp-ParametersMRDC-v1530 [9] PDCP-ParametersMRDC OPTIONAL,
   lateNonCriticalExtension [10] OCTET STRING (CONTAINING 
      UE-MRDC-Capability-v15g0) OPTIONAL,
   nonCriticalExtension [11] UE-MRDC-Capability-v1560 OPTIONAL
}

UE-NR-Capability-v16d0 ::= SEQUENCE {
   featureSets-v16d0 [0] FeatureSets-v16d0 OPTIONAL,
   nonCriticalExtension [1] SEQUENCE {

   } OPTIONAL
}

UE-NR-Capability-v16c0 ::= SEQUENCE {
   rf-Parameters-v16c0 [0] RF-Parameters-v16c0 OPTIONAL,
   nonCriticalExtension [1] UE-NR-Capability-v16d0 OPTIONAL
}

-- Late non-critical extensions from Rel-16 onwards:
UE-NR-Capability-v16a0 ::= SEQUENCE {
   phy-Parameters-v16a0 [0] Phy-Parameters-v16a0 OPTIONAL,
   rf-Parameters-v16a0 [1] RF-Parameters-v16a0 OPTIONAL,
   nonCriticalExtension [2] UE-NR-Capability-v16c0 OPTIONAL
}

UE-NR-Capability-v15j0 ::= SEQUENCE {
     -- Following field is only for REL-15 late non-critical extensions
   lateNonCriticalExtension [0] OCTET STRING OPTIONAL,
   nonCriticalExtension [1] UE-NR-Capability-v16a0 OPTIONAL
}

UE-NR-Capability-v15g0 ::= SEQUENCE {
   rf-Parameters-v15g0 [0] RF-Parameters-v15g0 OPTIONAL,
   nonCriticalExtension [1] UE-NR-Capability-v15j0 OPTIONAL
}

-- Late non-critical Rel-15 extensions:
UE-NR-Capability-v15c0 ::= SEQUENCE {
   nrdc-Parameters-v15c0 [0] NRDC-Parameters-v15c0 OPTIONAL,
   partialFR2-FallbackRX-Req [1] ENUMERATED { true(0) } OPTIONAL,
   nonCriticalExtension [2] UE-NR-Capability-v15g0 OPTIONAL
}

UE-NR-CapabilityAddXDD-Mode-v1530 ::= SEQUENCE {
   eutra-ParametersXDD-Diff [0] EUTRA-ParametersXDD-Diff
}

UE-NR-CapabilityAddFRX-Mode-v1540 ::= SEQUENCE {
   ims-ParametersFRX-Diff [0] IMS-ParametersFRX-Diff OPTIONAL
}

UE-NR-CapabilityAddFRX-Mode-v1610 ::= SEQUENCE {
   powSav-ParametersFRX-Diff-r16 [0] PowSav-ParametersFRX-Diff-r16 OPTIONAL,
   mac-ParametersFRX-Diff-r16 [1] MAC-ParametersFRX-Diff-r16 OPTIONAL
}

BAP-Parameters-r16 ::= SEQUENCE {
   flowControlBH-RLC-ChannelBased-r16 [0] ENUMERATED { supported(0) } OPTIONAL,
   flowControlRouting-ID-Based-r16 [1] ENUMERATED { supported(0) } OPTIONAL
}

BAP-Parameters-v1700 ::= SEQUENCE {
   bapHeaderRewriting-Rerouting-r17 [0] ENUMERATED { supported(0) } OPTIONAL,
   bapHeaderRewriting-Routing-r17 [1] ENUMERATED { supported(0) } OPTIONAL
}

MBS-Parameters-r17 ::= SEQUENCE {
   maxMRB-Add-r17 [0] INTEGER (1..16) OPTIONAL
}

-- TAG-UE-NR-CAPABILITY-STOP
-- TAG-UE-RADIOPAGINGINFO-START
UE-RadioPagingInfo-r17 ::= SEQUENCE {
     -- R1 29-1: Paging enhancement
   pei-SubgroupingSupportBandList-r17 [0] SEQUENCE (SIZE (1..maxBands)) OF 
      FreqBandIndicatorNR OPTIONAL,
   ...
}

UE-NR-Capability-v1750 ::= SEQUENCE {
   crossCarrierSchedulingConfigurationRelease-r17 [0] ENUMERATED { supported(0)
       } OPTIONAL,
   nonCriticalExtension [1] SEQUENCE {

   } OPTIONAL
}

UE-NR-Capability-v1740 ::= SEQUENCE {
   redCapParameters-v1740 [0] RedCapParameters-v1740,
   nonCriticalExtension [1] UE-NR-Capability-v1750 OPTIONAL
}

-- Regular non-critical Rel-17 extensions:
UE-NR-Capability-v1700 ::= SEQUENCE {
   inactiveStatePO-Determination-r17 [0] ENUMERATED { supported(0) } OPTIONAL,
   highSpeedParameters-v1700 [1] HighSpeedParameters-v1700 OPTIONAL,
   powSav-Parameters-v1700 [2] PowSav-Parameters-v1700 OPTIONAL,
   mac-Parameters-v1700 [3] MAC-Parameters-v1700 OPTIONAL,
   ims-Parameters-v1700 [4] IMS-Parameters-v1700 OPTIONAL,
   measAndMobParameters-v1700 [5] MeasAndMobParameters-v1700,
   appLayerMeasParameters-r17 [6] AppLayerMeasParameters-r17 OPTIONAL,
   redCapParameters-r17 [7] RedCapParameters-r17 OPTIONAL,
   ra-SDT-r17 [8] ENUMERATED { supported(0) } OPTIONAL,
   srb-SDT-r17 [9] ENUMERATED { supported(0) } OPTIONAL,
   gNB-SideRTT-BasedPDC-r17 [10] ENUMERATED { supported(0) } OPTIONAL,
   bh-RLF-DetectionRecovery-Indication-r17 [11] ENUMERATED { supported(0) }
       OPTIONAL,
   nrdc-Parameters-v1700 [12] NRDC-Parameters-v1700 OPTIONAL,
   bap-Parameters-v1700 [13] BAP-Parameters-v1700 OPTIONAL,
   musim-GapPreference-r17 [14] ENUMERATED { supported(0) } OPTIONAL,
   musimLeaveConnected-r17 [15] ENUMERATED { supported(0) } OPTIONAL,
   mbs-Parameters-r17 [16] MBS-Parameters-r17,
   nonTerrestrialNetwork-r17 [17] ENUMERATED { supported(0) } OPTIONAL,
   ntn-ScenarioSupport-r17 [18] ENUMERATED { gso(0), ngso(1) } OPTIONAL,
   sliceInfoforCellReselection-r17 [19] ENUMERATED { supported(0) } OPTIONAL,
   ue-RadioPagingInfo-r17 [20] UE-RadioPagingInfo-r17 OPTIONAL,
     -- R4 17-2 UL gap pattern for Tx power management
   ul-GapFR2-Pattern-r17 [21] BIT STRING  (SIZE (4)) OPTIONAL,
   ntn-Parameters-r17 [22] NTN-Parameters-r17 OPTIONAL,
   nonCriticalExtension [23] UE-NR-Capability-v1740 OPTIONAL
}

UE-NR-Capability-v1690 ::= SEQUENCE {
   ul-RRC-Segmentation-r16 [0] ENUMERATED { supported(0) } OPTIONAL,
   nonCriticalExtension [1] UE-NR-Capability-v1700 OPTIONAL
}

UE-NR-Capability-v1650 ::= SEQUENCE {
   mpsPriorityIndication-r16 [0] ENUMERATED { supported(0) } OPTIONAL,
   highSpeedParameters-v1650 [1] EXPLICIT HighSpeedParameters-v1650 OPTIONAL,
   nonCriticalExtension [2] UE-NR-Capability-v1690 OPTIONAL
}

UE-NR-Capability-v1640 ::= SEQUENCE {
   redirectAtResumeByNAS-r16 [0] ENUMERATED { supported(0) } OPTIONAL,
   phy-ParametersSharedSpectrumChAccess-r16 [1] 
      Phy-ParametersSharedSpectrumChAccess-r16 OPTIONAL,
   nonCriticalExtension [2] UE-NR-Capability-v1650 OPTIONAL
}

-- Regular non-critical Rel-16 extensions:
UE-NR-Capability-v1610 ::= SEQUENCE {
   inDeviceCoexInd-r16 [0] ENUMERATED { supported(0) } OPTIONAL,
   dl-DedicatedMessageSegmentation-r16 [1] ENUMERATED { supported(0) } OPTIONAL
      ,
   nrdc-Parameters-v1610 [2] NRDC-Parameters-v1610 OPTIONAL,
   powSav-Parameters-r16 [3] PowSav-Parameters-r16 OPTIONAL,
   fr1-Add-UE-NR-Capabilities-v1610 [4] UE-NR-CapabilityAddFRX-Mode-v1610
       OPTIONAL,
   fr2-Add-UE-NR-Capabilities-v1610 [5] UE-NR-CapabilityAddFRX-Mode-v1610
       OPTIONAL,
   bh-RLF-Indication-r16 [6] ENUMERATED { supported(0) } OPTIONAL,
   directSN-AdditionFirstRRC-IAB-r16 [7] ENUMERATED { supported(0) } OPTIONAL,
   bap-Parameters-r16 [8] BAP-Parameters-r16 OPTIONAL,
   referenceTimeProvision-r16 [9] ENUMERATED { supported(0) } OPTIONAL,
   sidelinkParameters-r16 [10] SidelinkParameters-r16 OPTIONAL,
   highSpeedParameters-r16 [11] HighSpeedParameters-r16 OPTIONAL,
   mac-Parameters-v1610 [12] MAC-Parameters-v1610 OPTIONAL,
   mcgRLF-RecoveryViaSCG-r16 [13] ENUMERATED { supported(0) } OPTIONAL,
   resumeWithStoredMCG-SCells-r16 [14] ENUMERATED { supported(0) } OPTIONAL,
   resumeWithStoredSCG-r16 [15] ENUMERATED { supported(0) } OPTIONAL,
   resumeWithSCG-Config-r16 [16] ENUMERATED { supported(0) } OPTIONAL,
   ue-BasedPerfMeas-Parameters-r16 [17] UE-BasedPerfMeas-Parameters-r16
       OPTIONAL,
   son-Parameters-r16 [18] SON-Parameters-r16 OPTIONAL,
   onDemandSIB-Connected-r16 [19] ENUMERATED { supported(0) } OPTIONAL,
   nonCriticalExtension [20] UE-NR-Capability-v1640 OPTIONAL
}

UE-NR-Capability-v1570 ::= SEQUENCE {
   nrdc-Parameters-v1570 [0] NRDC-Parameters-v1570 OPTIONAL,
   nonCriticalExtension [1] UE-NR-Capability-v1610 OPTIONAL
}

UE-NR-Capability-v1560 ::= SEQUENCE {
   nrdc-Parameters [0] NRDC-Parameters OPTIONAL,
   receivedFilters [1] OCTET STRING (CONTAINING UECapabilityEnquiry-v1560-IEs)
       OPTIONAL,
   nonCriticalExtension [2] UE-NR-Capability-v1570 OPTIONAL
}

UE-NR-Capability-v1550 ::= SEQUENCE {
   reducedCP-Latency [0] ENUMERATED { supported(0) } OPTIONAL,
   nonCriticalExtension [1] UE-NR-Capability-v1560 OPTIONAL
}

UE-NR-Capability-v1540 ::= SEQUENCE {
   sdap-Parameters [0] SDAP-Parameters OPTIONAL,
   overheatingInd [1] ENUMERATED { supported(0) } OPTIONAL,
   ims-Parameters [2] IMS-Parameters OPTIONAL,
   fr1-Add-UE-NR-Capabilities-v1540 [3] UE-NR-CapabilityAddFRX-Mode-v1540
       OPTIONAL,
   fr2-Add-UE-NR-Capabilities-v1540 [4] UE-NR-CapabilityAddFRX-Mode-v1540
       OPTIONAL,
   fr1-fr2-Add-UE-NR-Capabilities [5] UE-NR-CapabilityAddFRX-Mode OPTIONAL,
   nonCriticalExtension [6] UE-NR-Capability-v1550 OPTIONAL
}

-- Regular non-critical Rel-15 extensions:
UE-NR-Capability-v1530 ::= SEQUENCE {
   fdd-Add-UE-NR-Capabilities-v1530 [0] UE-NR-CapabilityAddXDD-Mode-v1530
       OPTIONAL,
   tdd-Add-UE-NR-Capabilities-v1530 [1] UE-NR-CapabilityAddXDD-Mode-v1530
       OPTIONAL,
   dummy [2] ENUMERATED { supported(0) } OPTIONAL,
   interRAT-Parameters [3] InterRAT-Parameters OPTIONAL,
   inactiveState [4] ENUMERATED { supported(0) } OPTIONAL,
   delayBudgetReporting [5] ENUMERATED { supported(0) } OPTIONAL,
   nonCriticalExtension [6] UE-NR-Capability-v1540 OPTIONAL
}

-- TAG-UE-MRDC-CAPABILITY-STOP
-- TAG-UE-NR-CAPABILITY-START
UE-NR-Capability ::= SEQUENCE {
   accessStratumRelease [0] AccessStratumRelease,
   pdcp-Parameters [1] PDCP-Parameters,
   rlc-Parameters [2] RLC-Parameters OPTIONAL,
   mac-Parameters [3] MAC-Parameters OPTIONAL,
   phy-Parameters [4] Phy-Parameters,
   rf-Parameters [5] RF-Parameters,
   measAndMobParameters [6] MeasAndMobParameters OPTIONAL,
   fdd-Add-UE-NR-Capabilities [7] UE-NR-CapabilityAddXDD-Mode OPTIONAL,
   tdd-Add-UE-NR-Capabilities [8] UE-NR-CapabilityAddXDD-Mode OPTIONAL,
   fr1-Add-UE-NR-Capabilities [9] UE-NR-CapabilityAddFRX-Mode OPTIONAL,
   fr2-Add-UE-NR-Capabilities [10] UE-NR-CapabilityAddFRX-Mode OPTIONAL,
   featureSets [11] FeatureSets OPTIONAL,
   featureSetCombinations [12] SEQUENCE (SIZE (1..maxFeatureSetCombinations)) OF FeatureSetCombination
       OPTIONAL,
   lateNonCriticalExtension [13] OCTET STRING (CONTAINING 
      UE-NR-Capability-v15c0) OPTIONAL,
   nonCriticalExtension [14] UE-NR-Capability-v1530 OPTIONAL
}

-- TAG-SL-SDAP-CONFIG-STOP
-- TAG-SL-SERVINGCELLINFO-START
SL-ServingCellInfo-r17 ::= SEQUENCE {
   sl-PhysCellId-r17 [0] PhysCellId,
   sl-CarrierFreqNR-r17 [1] ARFCN-ValueNR
}

-- Value assignments

maxAdditionalRACH-r17 INTEGER ::= 256

maxAI-DCI-PayloadSize-r16 INTEGER ::= 128

maxAI-DCI-PayloadSize-1-r16 INTEGER ::= 127

maxBandComb INTEGER ::= 65536

maxBandsUTRA-FDD-r16 INTEGER ::= 64

maxBH-RLC-ChannelID-r16 INTEGER ::= 65536

maxBT-IdReport-r16 INTEGER ::= 32

maxBT-Name-r16 INTEGER ::= 4

maxCAG-Cell-r16 INTEGER ::= 16

maxTwoPUCCH-Grp-ConfigList-r16 INTEGER ::= 32

maxTwoPUCCH-Grp-ConfigList-r17 INTEGER ::= 16

maxCBR-Config-r16 INTEGER ::= 8

maxCBR-Config-1-r16 INTEGER ::= 7

maxCBR-Level-r16 INTEGER ::= 16

maxCBR-Level-1-r16 INTEGER ::= 15

maxCellExcluded INTEGER ::= 16

maxCellGroupings-r16 INTEGER ::= 32

maxCellHistory-r16 INTEGER ::= 16

maxPSCellHistory-r17 INTEGER ::= 16

maxCellInter INTEGER ::= 16

maxCellIntra INTEGER ::= 16

maxCellMeasEUTRA INTEGER ::= 32

maxCellMeasIdle-r16 INTEGER ::= 8

maxCellMeasUTRA-FDD-r16 INTEGER ::= 32

maxCellNTN-r17 INTEGER ::= 4

maxCarrierTypePairList-r16 INTEGER ::= 16

maxCellAllowed INTEGER ::= 16

maxEARFCN INTEGER ::= 262143

maxEUTRA-CellExcluded INTEGER ::= 16

maxEUTRA-NS-Pmax INTEGER ::= 8

maxFeatureCombPreamblesPerRACHResource-r17 INTEGER ::= 256

maxLogMeasReport-r16 INTEGER ::= 520

maxMultiBands INTEGER ::= 8

maxNARFCN INTEGER ::= 3279165

maxNR-NS-Pmax INTEGER ::= 8

maxFreqIdle-r16 INTEGER ::= 8

maxNrofServingCells INTEGER ::= 32

maxNrofServingCells-1 INTEGER ::= 31

maxNrofAggregatedCellsPerCellGroup INTEGER ::= 16

maxNrofAggregatedCellsPerCellGroupMinus4-r16 INTEGER ::= 12

maxNrofDUCells-r16 INTEGER ::= 512

maxNrofAppLayerMeas-r17 INTEGER ::= 16

maxNrofAppLayerMeas-1-r17 INTEGER ::= 15

maxNrofAvailabilityCombinationsPerSet-r16 INTEGER ::= 512

maxNrofAvailabilityCombinationsPerSet-1-r16 INTEGER ::= 511

maxNrofIABResourceConfig-r17 INTEGER ::= 65536

maxNrofIABResourceConfig-1-r17 INTEGER ::= 65535

maxNrofSCellActRS-r17 INTEGER ::= 255

maxNrofSCells INTEGER ::= 31

maxNrofCellMeas INTEGER ::= 32

maxNrofCRS-IM-InterfCell-r17 INTEGER ::= 8

maxNrofRelayMeas-r17 INTEGER ::= 32

maxNrofCG-SL-r16 INTEGER ::= 8

maxNrofCG-SL-1-r16 INTEGER ::= 7

maxSL-GC-BC-DRX-QoS-r17 INTEGER ::= 16

maxNrofSL-RxInfoSet-r17 INTEGER ::= 4

maxNrofSS-BlocksToAverage INTEGER ::= 16

maxNrofCondCells-r16 INTEGER ::= 8

maxNrofCondCells-1-r17 INTEGER ::= 7

maxNrofCSI-RS-ResourcesToAverage INTEGER ::= 16

maxNrofDL-Allocations INTEGER ::= 16

maxNrofDL-AllocationsExt-r17 INTEGER ::= 64

maxNrofPDU-Sessions-r17 INTEGER ::= 256

maxNrofSR-ConfigPerCellGroup INTEGER ::= 8

maxLCG-ID INTEGER ::= 7

maxLCG-ID-IAB-r17 INTEGER ::= 255

maxLC-ID INTEGER ::= 32

maxLC-ID-Iab-r16 INTEGER ::= 65855

maxLTE-CRS-Patterns-r16 INTEGER ::= 3

maxNrofTAGs INTEGER ::= 4

maxNrofTAGs-1 INTEGER ::= 3

maxNrofBWPs INTEGER ::= 4

maxNrofCombIDC INTEGER ::= 128

maxNrofSymbols-1 INTEGER ::= 13

maxNrofSlots INTEGER ::= 320

maxNrofSlots-1 INTEGER ::= 319

maxNrofPhysicalResourceBlocks INTEGER ::= 275

maxNrofPhysicalResourceBlocks-1 INTEGER ::= 274

maxNrofPhysicalResourceBlocksPlus1 INTEGER ::= 276

maxNrofControlResourceSets INTEGER ::= 12

maxNrofControlResourceSets-1 INTEGER ::= 11

maxNrofControlResourceSets-1-r16 INTEGER ::= 15

maxNrofCoresetPools-r16 INTEGER ::= 2

maxCoReSetDuration INTEGER ::= 3

maxNrofSearchSpaces-1 INTEGER ::= 39

maxNrofSearchSpacesLinks-1-r17 INTEGER ::= 39

maxNrofBFDResourcePerSet-r17 INTEGER ::= 64

maxSFI-DCI-PayloadSize INTEGER ::= 128

maxSFI-DCI-PayloadSize-1 INTEGER ::= 127

maxIAB-IP-Address-r16 INTEGER ::= 32

maxINT-DCI-PayloadSize INTEGER ::= 126

maxINT-DCI-PayloadSize-1 INTEGER ::= 125

maxNrofRateMatchPatterns INTEGER ::= 4

maxNrofRateMatchPatterns-1 INTEGER ::= 3

maxNrofRateMatchPatternsPerGroup INTEGER ::= 8

maxNrofCSI-ReportConfigurations INTEGER ::= 48

maxNrofCSI-ReportConfigurations-1 INTEGER ::= 47

maxNrofCSI-ResourceConfigurations INTEGER ::= 112

maxNrofCSI-ResourceConfigurations-1 INTEGER ::= 111

maxNrofAP-CSI-RS-ResourcesPerSet INTEGER ::= 16

maxNrOfCSI-AperiodicTriggers INTEGER ::= 128

maxNrofReportConfigPerAperiodicTrigger INTEGER ::= 16

maxNrofNZP-CSI-RS-Resources INTEGER ::= 192

maxNrofNZP-CSI-RS-Resources-1 INTEGER ::= 191

maxNrofNZP-CSI-RS-ResourcesPerSet INTEGER ::= 64

maxNrofNZP-CSI-RS-ResourceSets INTEGER ::= 64

maxNrofNZP-CSI-RS-ResourceSets-1 INTEGER ::= 63

maxNrofNZP-CSI-RS-ResourceSetsPerConfig INTEGER ::= 16

maxNrofNZP-CSI-RS-ResourcesPerConfig INTEGER ::= 128

maxNrofZP-CSI-RS-Resources INTEGER ::= 32

maxNrofZP-CSI-RS-Resources-1 INTEGER ::= 31

maxNrofZP-CSI-RS-ResourceSets-1 INTEGER ::= 15

maxNrofZP-CSI-RS-ResourcesPerSet INTEGER ::= 16

maxNrofZP-CSI-RS-ResourceSets INTEGER ::= 16

maxNrofCSI-IM-Resources INTEGER ::= 32

maxNrofCSI-IM-Resources-1 INTEGER ::= 31

maxNrofCSI-IM-ResourcesPerSet INTEGER ::= 8

maxNrofCSI-IM-ResourceSets INTEGER ::= 64

maxNrofCSI-IM-ResourceSets-1 INTEGER ::= 63

maxNrofCSI-IM-ResourceSetsPerConfig INTEGER ::= 16

maxNrofCSI-SSB-ResourcePerSet INTEGER ::= 64

maxNrofCSI-SSB-ResourceSets INTEGER ::= 64

maxNrofCSI-SSB-ResourceSets-1 INTEGER ::= 63

maxNrofCSI-SSB-ResourceSetsPerConfig INTEGER ::= 1

maxNrofCSI-SSB-ResourceSetsPerConfigExt INTEGER ::= 2

maxNrofFailureDetectionResources INTEGER ::= 10

maxNrofFailureDetectionResources-1 INTEGER ::= 9

maxNrofFailureDetectionResources-1-r17 INTEGER ::= 63

maxNrofFreqSL-r16 INTEGER ::= 8

maxNrofSL-BWPs-r16 INTEGER ::= 4

maxFreqSL-EUTRA-r16 INTEGER ::= 8

maxNrofSL-MeasId-r16 INTEGER ::= 64

maxNrofSL-ObjectId-r16 INTEGER ::= 64

maxNrofSL-ReportConfigId-r16 INTEGER ::= 64

maxNrofSL-PoolToMeasureNR-r16 INTEGER ::= 8

maxFreqSL-NR-r16 INTEGER ::= 8

maxNrofSL-QFIs-r16 INTEGER ::= 2048

maxNrofSL-QFIsPerDest-r16 INTEGER ::= 64

maxNrofObjectId INTEGER ::= 64

maxNrofPageRec INTEGER ::= 32

maxNrofPCI-Ranges INTEGER ::= 8

maxPLMN INTEGER ::= 12

maxTAC-r17 INTEGER ::= 12

maxNrofCSI-RS-ResourcesRRM INTEGER ::= 96

maxNrofCSI-RS-ResourcesRRM-1 INTEGER ::= 95

maxNrofMeasId INTEGER ::= 64

maxNrofQuantityConfig INTEGER ::= 2

maxNrofCSI-RS-CellsRRM INTEGER ::= 96

maxNrofSL-Dest-r16 INTEGER ::= 32

maxNrofSL-Dest-1-r16 INTEGER ::= 31

maxNrofSLRB-r16 INTEGER ::= 512

maxSL-LCID-r16 INTEGER ::= 512

maxSL-SyncConfig-r16 INTEGER ::= 16

maxNrofRXPool-r16 INTEGER ::= 16

maxNrofTXPool-r16 INTEGER ::= 8

maxNrofPoolID-r16 INTEGER ::= 16

maxNrofSRS-PathlossReferenceRS-r16 INTEGER ::= 64

maxNrofSRS-PathlossReferenceRS-1-r16 INTEGER ::= 63

maxNrofSRS-ResourceSets INTEGER ::= 16

maxNrofSRS-ResourceSets-1 INTEGER ::= 15

maxNrofSRS-PosResourceSets-r16 INTEGER ::= 16

maxNrofSRS-PosResourceSets-1-r16 INTEGER ::= 15

maxNrofSRS-Resources INTEGER ::= 64

maxNrofSRS-Resources-1 INTEGER ::= 63

maxNrofSRS-PosResources-r16 INTEGER ::= 64

maxNrofSRS-PosResources-1-r16 INTEGER ::= 63

maxNrofSRS-ResourcesPerSet INTEGER ::= 16

maxNrofSRS-TriggerStates-1 INTEGER ::= 3

maxNrofSRS-TriggerStates-2 INTEGER ::= 2

maxRAT-CapabilityContainers INTEGER ::= 8

maxSimultaneousBands INTEGER ::= 32

maxULTxSwitchingBandPairs INTEGER ::= 32

maxNrofSlotFormatCombinationsPerSet INTEGER ::= 512

maxNrofSlotFormatCombinationsPerSet-1 INTEGER ::= 511

maxNrofTrafficPattern-r16 INTEGER ::= 8

maxNrofPUCCH-Resources INTEGER ::= 128

maxNrofPUCCH-Resources-1 INTEGER ::= 127

maxNrofPUCCH-ResourceSets INTEGER ::= 4

maxNrofPUCCH-ResourceSets-1 INTEGER ::= 3

maxNrofPUCCH-ResourcesPerSet INTEGER ::= 32

maxNrofPUCCH-P0-PerSet INTEGER ::= 8

maxNrofPUCCH-PathlossReferenceRSs INTEGER ::= 4

maxNrofPUCCH-PathlossReferenceRSs-1 INTEGER ::= 3

maxNrofPUCCH-PathlossReferenceRSs-r16 INTEGER ::= 64

maxNrofPUCCH-PathlossReferenceRSs-1-r16 INTEGER ::= 63

maxNrofPUCCH-PathlossReferenceRSs-1-r17 INTEGER ::= 7

maxNrofPUCCH-PathlossReferenceRSsDiff-r16 INTEGER ::= 60

maxNrofPUCCH-ResourceGroups-r16 INTEGER ::= 4

maxNrofPUCCH-ResourcesPerGroup-r16 INTEGER ::= 128

maxNrofPowerControlSetInfos-r17 INTEGER ::= 8

maxNrofMultiplePUSCHs-r16 INTEGER ::= 8

maxNrofP0-PUSCH-AlphaSets INTEGER ::= 30

maxNrofP0-PUSCH-AlphaSets-1 INTEGER ::= 29

maxNrofPUSCH-PathlossReferenceRSs INTEGER ::= 4

maxNrofPUSCH-PathlossReferenceRSs-1 INTEGER ::= 3

maxNrofPUSCH-PathlossReferenceRSs-r16 INTEGER ::= 64

maxNrofPUSCH-PathlossReferenceRSs-1-r16 INTEGER ::= 63

maxNrofPUSCH-PathlossReferenceRSsDiff-r16 INTEGER ::= 60

maxNrofPathlossReferenceRSs-r17 INTEGER ::= 64

maxNrofPathlossReferenceRSs-1-r17 INTEGER ::= 63

maxNrofNAICS-Entries INTEGER ::= 8

maxBands INTEGER ::= 1024

maxBandsMRDC INTEGER ::= 1280

maxBandsEUTRA INTEGER ::= 256

maxCellReport INTEGER ::= 8

maxDRB INTEGER ::= 29

maxFreq INTEGER ::= 8

maxFreqLayers INTEGER ::= 4

maxFreqPlus1 INTEGER ::= 9

maxFreqIDC-r16 INTEGER ::= 128

maxCombIDC-r16 INTEGER ::= 128

maxFreqIDC-MRDC INTEGER ::= 32

maxNrofCandidateBeams INTEGER ::= 16

maxNrofCandidateBeams-r16 INTEGER ::= 64

maxNrofCandidateBeamsExt-r16 INTEGER ::= 48

maxNrofPCIsPerSMTC INTEGER ::= 64

maxNrofQFIs INTEGER ::= 64

maxNrofResourceAvailabilityPerCombination-r16 INTEGER ::= 256

maxNrOfSemiPersistentPUSCH-Triggers INTEGER ::= 64

maxNrofSR-Resources INTEGER ::= 8

maxNrofSlotFormatsPerCombination INTEGER ::= 256

maxNrofSpatialRelationInfos INTEGER ::= 8

maxNrofSpatialRelationInfos-plus-1 INTEGER ::= 9

maxNrofSpatialRelationInfos-r16 INTEGER ::= 64

maxNrofSpatialRelationInfosDiff-r16 INTEGER ::= 56

maxNrofIndexesToReport INTEGER ::= 32

maxNrofIndexesToReport2 INTEGER ::= 64

maxNrofSSBs-r16 INTEGER ::= 64

maxNrofSSBs-1 INTEGER ::= 63

maxNrofS-NSSAI INTEGER ::= 8

maxNrofTCI-StatesPDCCH INTEGER ::= 64

maxNrofTCI-States INTEGER ::= 128

maxNrofTCI-States-1 INTEGER ::= 127

maxUL-TCI-r17 INTEGER ::= 64

maxUL-TCI-1-r17 INTEGER ::= 63

maxNrofAdditionalPCI-r17 INTEGER ::= 7

maxMPE-Resources-r17 INTEGER ::= 64

maxNrofUL-Allocations INTEGER ::= 16

maxQFI INTEGER ::= 63

maxRA-CSIRS-Resources INTEGER ::= 96

maxRA-OccasionsPerCSIRS INTEGER ::= 64

maxRA-Occasions-1 INTEGER ::= 511

maxRA-SSB-Resources INTEGER ::= 64

maxSCSs INTEGER ::= 5

maxSecondaryCellGroups INTEGER ::= 3

maxNrofServingCellsEUTRA INTEGER ::= 32

maxMBSFN-Allocations INTEGER ::= 8

maxNrofMultiBands INTEGER ::= 8

maxCellSFTD INTEGER ::= 3

maxReportConfigId INTEGER ::= 64

maxNrofCodebooks INTEGER ::= 16

maxNrofCSI-RS-ResourcesExt-r16 INTEGER ::= 16

maxNrofCSI-RS-ResourcesExt-r17 INTEGER ::= 8

maxNrofCSI-RS-Resources INTEGER ::= 7

maxNrofCSI-RS-ResourcesAlt-r16 INTEGER ::= 512

maxNrofCSI-RS-ResourcesAlt-1-r16 INTEGER ::= 511

maxNrofSRI-PUSCH-Mappings INTEGER ::= 16

maxNrofSRI-PUSCH-Mappings-1 INTEGER ::= 15

maxSIB INTEGER ::= 32

maxSI-Message INTEGER ::= 32

maxSIB-MessagePlus1-r17 INTEGER ::= 33

maxPO-perPF INTEGER ::= 4

maxPEI-perPF-r17 INTEGER ::= 4

maxAccessCat-1 INTEGER ::= 63

maxBarringInfoSet INTEGER ::= 8

maxCellEUTRA INTEGER ::= 8

maxEUTRA-Carrier INTEGER ::= 8

maxPLMNIdentities INTEGER ::= 8

maxDownlinkFeatureSets INTEGER ::= 1024

maxUplinkFeatureSets INTEGER ::= 1024

maxEUTRA-DL-FeatureSets INTEGER ::= 256

maxEUTRA-UL-FeatureSets INTEGER ::= 256

maxFeatureSetsPerBand INTEGER ::= 128

maxPerCC-FeatureSets INTEGER ::= 1024

maxFeatureSetCombinations INTEGER ::= 1024

maxInterRAT-RSTD-Freq INTEGER ::= 3

maxGIN-r17 INTEGER ::= 24

maxHRNN-Len-r16 INTEGER ::= 48

maxNPN-r16 INTEGER ::= 12

maxNrOfMinSchedulingOffsetValues-r16 INTEGER ::= 2

maxK0-SchedulingOffset-r16 INTEGER ::= 16

maxK2-SchedulingOffset-r16 INTEGER ::= 16

maxK0-SchedulingOffset-r17 INTEGER ::= 64

maxK2-SchedulingOffset-r17 INTEGER ::= 64

maxDCI-2-6-Size-r16 INTEGER ::= 140

maxDCI-2-7-Size-r17 INTEGER ::= 43

maxDCI-2-6-Size-1-r16 INTEGER ::= 139

maxNrofUL-Allocations-r16 INTEGER ::= 64

maxNrofP0-PUSCH-Set-r16 INTEGER ::= 2

maxOnDemandSIB-r16 INTEGER ::= 8

maxOnDemandPosSIB-r16 INTEGER ::= 32

maxCI-DCI-PayloadSize-r16 INTEGER ::= 126

maxCI-DCI-PayloadSize-1-r16 INTEGER ::= 125

maxUu-RelayRLC-ChannelID-r17 INTEGER ::= 32

maxWLAN-Id-Report-r16 INTEGER ::= 32

maxWLAN-Name-r16 INTEGER ::= 4

maxRAReport-r16 INTEGER ::= 8

maxTxConfig-r16 INTEGER ::= 64

maxTxConfig-1-r16 INTEGER ::= 63

maxPSSCH-TxConfig-r16 INTEGER ::= 16

maxNrofCLI-RSSI-Resources-r16 INTEGER ::= 64

maxNrofCLI-RSSI-Resources-1-r16 INTEGER ::= 63

maxNrofCLI-SRS-Resources-r16 INTEGER ::= 32

maxCLI-Report-r16 INTEGER ::= 8

maxNrofCC-Group-r17 INTEGER ::= 16

maxNrofConfiguredGrantConfig-r16 INTEGER ::= 12

maxNrofConfiguredGrantConfig-1-r16 INTEGER ::= 11

maxNrofCG-Type2DeactivationState INTEGER ::= 16

maxNrofConfiguredGrantConfigMAC-1-r16 INTEGER ::= 31

maxNrofSPS-Config-r16 INTEGER ::= 8

maxNrofSPS-Config-1-r16 INTEGER ::= 7

maxNrofSPS-DeactivationState INTEGER ::= 16

maxNrofPPW-Config-r17 INTEGER ::= 4

maxNrofPPW-ID-1-r17 INTEGER ::= 15

maxNrOfTxTEGReport-r17 INTEGER ::= 256

maxNrOfTxTEG-ID-1-r17 INTEGER ::= 7

maxNrofPagingSubgroups-r17 INTEGER ::= 8

maxNrofPUCCH-ResourceGroups-1-r16 INTEGER ::= 3

maxNrofReqComDC-Location-r17 INTEGER ::= 128

maxNrofServingCellsTCI-r16 INTEGER ::= 32

maxNrofTxDC-TwoCarrier-r16 INTEGER ::= 64

maxNrofRB-SetGroups-r17 INTEGER ::= 8

maxNrofRB-Sets-r17 INTEGER ::= 8

maxNrofEnhType3HARQ-ACK-r17 INTEGER ::= 8

maxNrofEnhType3HARQ-ACK-1-r17 INTEGER ::= 7

maxNrofPRS-ResourcesPerSet-r17 INTEGER ::= 64

maxNrofPRS-ResourcesPerSet-1-r17 INTEGER ::= 63

maxNrofPRS-ResourceOffsetValue-1-r17 INTEGER ::= 511

maxNrofGapId-r17 INTEGER ::= 8

maxNrofPreConfigPosGapId-r17 INTEGER ::= 16

maxNrOfGapPri-r17 INTEGER ::= 16

maxCEFReport-r17 INTEGER ::= 4

maxNrofMultiplePDSCHs-r17 INTEGER ::= 8

maxSliceInfo-r17 INTEGER ::= 8

maxCellSlice-r17 INTEGER ::= 16

maxNrofTRS-ResourceSets-r17 INTEGER ::= 64

maxNrofSearchSpaceGroups-1-r17 INTEGER ::= 2

maxNrofRemoteUE-r17 INTEGER ::= 32

maxDCI-4-2-Size-r17 INTEGER ::= 140

maxFreqMBS-r17 INTEGER ::= 16

maxNrofDRX-ConfigPTM-r17 INTEGER ::= 64

maxNrofDRX-ConfigPTM-1-r17 INTEGER ::= 63

maxNrofMBS-ServiceListPerUE-r17 INTEGER ::= 16

maxNrofMBS-Session-r17 INTEGER ::= 1024

maxNrofMTCH-SSB-MappingWindow-r17 INTEGER ::= 16

maxNrofMTCH-SSB-MappingWindow-1-r17 INTEGER ::= 15

maxNrofMRB-Broadcast-r17 INTEGER ::= 4

maxNrofPageGroup-r17 INTEGER ::= 32

maxNrofPDSCH-ConfigPTM-r17 INTEGER ::= 16

maxNrofPDSCH-ConfigPTM-1-r17 INTEGER ::= 15

maxG-RNTI-r17 INTEGER ::= 16

maxG-RNTI-1-r17 INTEGER ::= 15

maxG-CS-RNTI-r17 INTEGER ::= 8

maxG-CS-RNTI-1-r17 INTEGER ::= 7

maxMRB-r17 INTEGER ::= 32

maxFSAI-MBS-r17 INTEGER ::= 64

maxNeighCellMBS-r17 INTEGER ::= 8

maxNrofPdcch-BlindDetectionMixed-1-r16 INTEGER ::= 7

maxNrofPdcch-BlindDetection-r17 INTEGER ::= 16


END
